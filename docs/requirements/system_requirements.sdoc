[DOCUMENT]
TITLE: System Requirements
UID: YAAP-SR
DATE: @GIT_COMMIT_DATETIME
PREFIX: SR-

[[SECTION]]
TITLE: Introduction

[TEXT]
STATEMENT: >>>
This document defines the system requirements for Yet Another Audio Player (Yaap),
a time accurate desktop audio player.
<<<

[[/SECTION]]

[[SECTION]]
TITLE: Main App

[[SECTION]]
TITLE: Audio Playback

[[SECTION]]
TITLE: Audio Format Support

[REQUIREMENT]
UID: SR-001
TITLE: FLAC Audio Support
STATEMENT: >>>
The system shall support playback of audio files encoded in the FLAC format.
<<<
RELATIONS:
- TYPE: Parent
  VALUE: UR-001

[REQUIREMENT]
UID: SR-002
TITLE: MP3 Audio Support
STATEMENT: >>>
The system shall support playback of audio files encoded in the MP3 format.
<<<
RELATIONS:
- TYPE: Parent
  VALUE: UR-001

[REQUIREMENT]
UID: SR-003
TITLE: WAV Audio Support
STATEMENT: >>>
The system shall support playback of audio files containing supported PCM audio 
in the WAV container format.
<<<
RELATIONS:
- TYPE: Parent
  VALUE: UR-001

[REQUIREMENT]
UID: SR-004
TITLE: AAC Audio Support
STATEMENT: >>>
The system shall support playback of audio files encoded in the AAC codec in 
supported containers, including M4A audio files.
<<<
RELATIONS:
- TYPE: Parent
  VALUE: UR-001

[REQUIREMENT]
UID: SR-005
TITLE: ALAC Audio Support
STATEMENT: >>>
The system shall support playback of audio files encoded in the ALAC format.
<<<
RELATIONS:
- TYPE: Parent
  VALUE: UR-001

[REQUIREMENT]
UID: SR-006
TITLE: Vorbis Audio Support
STATEMENT: >>>
The system shall support playback of audio files encoded in the Vorbis codec in
supported containers, including OGG files.
<<<
RELATIONS:
- TYPE: Parent
  VALUE: UR-001

[REQUIREMENT]
UID: SR-007
TITLE: Opus Audio Support
STATEMENT: >>>
The system shall support playback of audio files encoded in the Opus codec in 
supported containers.
<<<
RELATIONS:
- TYPE: Parent
  VALUE: UR-001

[REQUIREMENT]
UID: SR-008
TITLE: AIFF Audio Support
STATEMENT: >>>
The system shall support playback of audio files containing supported PCM audio 
in the AIFF container format.
<<<
RELATIONS:
- TYPE: Parent
  VALUE: UR-001

[[/SECTION]]

[[SECTION]]
TITLE: General Audio Decoding

[REQUIREMENT]
UID: SR-009
TITLE: Audio Format Identification
STATEMENT: >>>
The system shall identify the audio format of an input file using its content or 
format metadata rather then relying solely on its file extension.
<<<
RELATIONS:
- TYPE: Parent
  VALUE: UR-001

[REQUIREMENT]
UID: SR-010
TITLE: Unsupported Audio Formats
STATEMENT: >>>
The system shall report when an audio file cannot be played because its format or
encoding is unsupported.
<<<
RELATIONS:
- TYPE: Parent
  VALUE: UR-002

[REQUIREMENT]
UID: SR-011
TITLE: Invalid Audio Files
STATEMENT: >>>
The system shall report an appropriate error when an audio file cannot be decoded
because its contents are invalid or corrupted.
<<<
RELATIONS:
- TYPE: Parent
  VALUE: UR-002

[[/SECTION]]

[[SECTION]]
TITLE: Local Audio Files

[REQUIREMENT]
UID: SR-012
TITLE: Local Audio File Selection
STATEMENT: >>>
The system shall allow for a local audio file to be browsed or selected for
playback.
<<<
RELATIONS:
- TYPE: Parent
  VALUE: UR-003

[REQUIREMENT]
UID: SR-013
TITLE: Local Audio File Playback
STATEMENT: >>>
The system shall play audio from a selected local audio file when its container
format and encoding are supported.
<<<
RELATIONS:
- TYPE: Parent
  VALUE: UR-003

[REQUIREMENT]
UID: SR-014
TITLE: Local File Access Failure
STATEMENT: >>>
The system shall report when a selected local audio file cannot be accessed for 
playback.
<<<
RELATIONS:
- TYPE: Parent
  VALUE: UR-003

[REQUIREMENT]
UID: SR-124
TITLE: Local Audio File Playback Failure
STATEMENT: >>>
The system shall report when a selected local audio file cannot be played.
<<<
RELATIONS:
- TYPE: Parent
  VALUE: UR-003

[[/SECTION]]

[[SECTION]]
TITLE: Cloud Storage Provider Support

[REQUIREMENT]
UID: SR-015
TITLE: Supported Cloud Storage Providers
STATEMENT: >>>
The system shall support the following cloud storage providers:
Google Drive, iCloud Drive, Dropbox, and Microsoft OneDrive.
<<<
RELATIONS:
- TYPE: Parent
  VALUE: UR-004

[REQUIREMENT]
UID: SR-016
TITLE: Cloud Storage Provider Authentication
STATEMENT: >>>
The system shall support authenticating with each supported cloud storage
provider.
<<<
RELATIONS:
- TYPE: Parent
  VALUE: UR-004

[REQUIREMENT]
UID: SR-018
TITLE: Cloud Storage Provider Authentication Failure
STATEMENT: >>>
The system shall report when authentication with a cloud storage provider
fails.
<<<
RELATIONS:
- TYPE: Parent
  VALUE: UR-004

[REQUIREMENT]
UID: SR-135
TITLE: Cloud Storage Provider Authentication Expiration
STATEMENT: >>>
The system shall report when authentication with a cloud storage provider
expires.
<<<
RELATIONS:
- TYPE: Parent
  VALUE: UR-004

[REQUIREMENT]
UID: SR-127
TITLE: Cloud Storage Provider Connection
STATEMENT: >>>
The system shall support establishing connections to supported cloud storage 
providers.
<<<
RELATIONS:
- TYPE: Parent
  VALUE: UR-004

[REQUIREMENT]
UID: SR-129
TITLE: Cloud Storage Provider Disconnection 
STATEMENT: >>>
The system shall support disconnecting from supported cloud storage providers.
<<<
RELATIONS:
- TYPE: Parent
  VALUE: UR-004

[REQUIREMENT]
UID: SR-017
TITLE: Cloud Connection Status
STATEMENT: >>>
The system shall report the connection status of each configured cloud storage
provider.
<<<
RELATIONS:
- TYPE: Parent
  VALUE: UR-004

[REQUIREMENT]
UID: SR-136
TITLE: Cloud Connection Failure
STATEMENT: >>>
The system shall detect and report when a connection to a cloud storage 
provider fails.
<<<
RELATIONS:
- TYPE: Parent
  VALUE: UR-004

[REQUIREMENT]
UID: SR-130
TITLE: Cloud Storage Provider Interruption
STATEMENT: >>>
The system shall detect and report when an established connection
to a cloud storage provider is interrupted.
<<<
RELATIONS:
- TYPE: Parent
  VALUE: UR-004

[REQUIREMENT]
UID: SR-137
TITLE: Cloud Storage Provider Reconnection
STATEMENT: >>>
The system shall support re-establishing interrupted or expired connections to 
supported cloud storage providers.
<<<
RELATIONS:
- TYPE: Parent
  VALUE: UR-004

[[/SECTION]]

[[SECTION]]
TITLE: Remote Audio Files

[REQUIREMENT]
UID: SR-019
TITLE: Remote Audio File Selection
STATEMENT: >>>
The system shall allow for remote audio files to be browsed or selected for 
playback through connected cloud storage providers.
<<<
RELATIONS:
- TYPE: Parent
  VALUE: UR-005

[REQUIREMENT]
UID: SR-020
TITLE: Remote Audio File Playback
STATEMENT: >>>
The system shall play a selected remote audio file when its format and encoding 
are supported and the file is accessible.
<<<
RELATIONS:
- TYPE: Parent
  VALUE: UR-005

[REQUIREMENT]
UID: SR-021
TITLE: Remote Audio File Access Failure
STATEMENT: >>>
The system shall report when a selected remote audio file cannot be retrieved
for playback.
<<<
RELATIONS:
- TYPE: Parent
  VALUE: UR-005

[REQUIREMENT]
UID: SR-022
TITLE: Remote Audio File Playback Failure
STATEMENT: >>>
The system shall report when a selected remote audio file cannot be played.
<<<
RELATIONS:
- TYPE: Parent
  VALUE: UR-005

[REQUIREMENT]
UID: SR-128
TITLE: Remote Audio Playback Interruption
STATEMENT: >>>
The system shall report when a remote audio file becomes unavailable during
playback and playback cannot continue.
<<<
RELATIONS:
- TYPE: Parent
  VALUE: UR-005

[REQUIREMENT]
UID: SR-138
TITLE: Remote Audio Playback Recovery
STATEMENT: >>>
The system shall support resuming interrupted remote audio playback when the 
remote audio file becomes accessible again.
<<<
RELATIONS:
- TYPE: Parent
  VALUE: UR-005

[[/SECTION]]

[[SECTION]]
TITLE: Audio Quality

[REQUIREMENT]
UID: SR-023
TITLE: Audio Decoding Fidelity
STATEMENT: >>>
The system shall decode supported audio files in accordance with their encoding 
formats without introducing additional loss of audio information.
<<<
RELATIONS:
- TYPE: Parent
  VALUE: UR-006

[[/SECTION]]

[[SECTION]]
TITLE: Audio Playback Position

[REQUIREMENT]
UID: SR-024
TITLE: Playback Position Accuracy
STATEMENT: >>>
The system shall report the playback position within the greater of 1 
microsecond or the temporal resolution of the active audio track.
<<<
RELATIONS:
- TYPE: Parent
  VALUE: UR-007

[REQUIREMENT]
UID: SR-025
TITLE: Playback Position Availability
STATEMENT: >>>
The system shall make the current playback position of the active audio track 
available to the user.
<<<
RELATIONS:
- TYPE: Parent
  VALUE: UR-007

[REQUIREMENT]
UID: SR-026
TITLE: Elapsed Playback Time
STATEMENT: >>>
The system shall report the elapsed playback time of the active audio track, 
corresponding to its current playback position.
<<<
RELATIONS:
- TYPE: Parent
  VALUE: UR-007
- TYPE: Parent
  VALUE: UR-008

[REQUIREMENT]
UID: SR-027
TITLE: Playback Position Seeking
STATEMENT: >>>
The system shall allow the user to request a playback position within the duration 
of the active audio track.
<<<
RELATIONS:
- TYPE: Parent
  VALUE: UR-009

[REQUIREMENT]
UID: SR-028
TITLE: Seek Position Accuracy
STATEMENT: >>>
The system shall seek to the requested playback position with the greater of 1 
microsecond or the temporal resolution of the active audio track.
<<<
RELATIONS:
- TYPE: Parent
  VALUE: UR-009

[REQUIREMENT]
UID: SR-029
TITLE: Remaining Playback Time
STATEMENT: >>>
The system shall display the estimated remaining playback time of the active audio
track, calculated from its duration and current playback position.
<<<
RELATIONS:
- TYPE: Parent
  VALUE: UR-010

[REQUIREMENT]
UID: SR-030
TITLE: Media Playback Information
STATEMENT: >>>
The system shall make the currently playing track's playback information 
accessible through the operating system's media-control interface, where
supported by that interface.
<<<
RELATIONS:
- TYPE: Parent
  VALUE: UR-011

[REQUIREMENT]
UID: SR-031
TITLE: Media Playback Metadata
STATEMENT: >>>
The system shall make the currently playing track's metadata accessible through 
the operating system's media-control interface, where supported by that interface.
<<<
RELATIONS:
- TYPE: Parent
  VALUE: UR-011

[REQUIREMENT]
UID: SR-032
TITLE: Media Playback Controls
STATEMENT: >>>
The system shall support playback control commands received through the operating 
system's media-control interface, where supported by that interface.
<<<
RELATIONS:
- TYPE: Parent
  VALUE: UR-011

[[/SECTION]]

[[SECTION]]
TITLE: Audio Playback Customization

[REQUIREMENT]
UID: SR-033
TITLE: Playback Speed Adjustment
STATEMENT: >>>
The system shall support the adjustment of the playback speed of the active 
audio track.
<<<
RELATIONS:
- TYPE: Parent
  VALUE: UR-012

[REQUIREMENT]
UID: SR-034
TITLE: Playback Speed Range
STATEMENT: >>>
The system shall support playback speeds from 0.5x to 2.0x inclusive at 
minimum.
<<<
RELATIONS:
- TYPE: Parent
  VALUE: UR-012

[REQUIREMENT]
UID: SR-035
TITLE: Independent Playback Pitch Adjustment
STATEMENT: >>>
The system shall support the adjustment of the playback pitch independently of 
playback speed.
<<<
RELATIONS:
- TYPE: Parent
  VALUE: UR-013

[REQUIREMENT]
UID: SR-036
TITLE: Playback Pitch Range
STATEMENT: >>>
The system shall support playback pitch adjustments from -6 to +6 semitones
inclusive at minimum.
<<<
RELATIONS:
- TYPE: Parent
  VALUE: UR-013

[REQUIREMENT]
UID: SR-037
TITLE: Playback Volume Adjustment
STATEMENT: >>>
The system shall support the adjustment of the playback volume within a range 
of 0% (silence) to 150% (1.5 times the reference amplitude), inclusive.
<<<
RELATIONS:
- TYPE: Parent
  VALUE: UR-014

[REQUIREMENT]
UID: SR-038
TITLE: Audio Processing Configuration
STATEMENT: >>>
The system shall allow the user to configure each supported audio processing 
option.
<<<
RELATIONS:
- TYPE: Parent
  VALUE: UR-015

[REQUIREMENT]
UID: SR-039
TITLE: Active Playback Customisation Information
STATEMENT: >>>
The system shall make the currently active playback speed, pitch adjustment, 
volume setting and audio processing options available for display to the user.
<<<
RELATIONS:
- TYPE: Parent
  VALUE: UR-016

[[/SECTION]]

[[/SECTION]]

[[SECTION]]
TITLE: Audio Tracks

[[SECTION]]
TITLE: Track Metadata

[REQUIREMENT]
UID: SR-040
TITLE: Displaying Track Metadata
STATEMENT: >>>
The system shall allow for the viewing of available metadata for a selected
audio track.
<<<
RELATIONS:
- TYPE: Parent
  VALUE: UR-027

[REQUIREMENT]
UID: SR-041
TITLE: Editing Track Metadata
STATEMENT: >>>
The system shall allow for the modification of metadata fields that are editable 
for a selected audio track.
<<<
RELATIONS:
- TYPE: Parent
  VALUE: UR-028

[REQUIREMENT]
UID: SR-042
TITLE: Editing Track Metadata
STATEMENT: >>>
The system shall allow for the deletion of metadata fields that are editable 
for a selected audio track.
<<<
RELATIONS:
- TYPE: Parent
  VALUE: UR-028

[REQUIREMENT]
UID: SR-043
TITLE: Saving Track Metadata
STATEMENT: >>>
The system shall allow metadata changes made to an audio track to be saved.
<<<
RELATIONS:
- TYPE: Parent
  VALUE: UR-029

[REQUIREMENT]
UID: SR-044
TITLE: Reporting Metadata Save Results
STATEMENT: >>>
The system shall report if metadata changes were saved successfully.
<<<
RELATIONS:
- TYPE: Parent
  VALUE: UR-029

[REQUIREMENT]
UID: SR-045
TITLE: Reporting Metadata Save Results
STATEMENT: >>>
The system shall report an error if atempting to save metadata changes fails.
<<<
RELATIONS:
- TYPE: Parent
  VALUE: UR-029

[REQUIREMENT]
UID: SR-046
TITLE: Identifying Non-Editable Metadata Fields
STATEMENT: >>>
The system shall distinguish metadata fields that cannot be modified from fields 
that can be modified.
<<<
RELATIONS:
- TYPE: Parent
  VALUE: UR-030

[[/SECTION]]

[[SECTION]]
TITLE: Undoing and Redoing Actions

[REQUIREMENT]
UID: SR-125
TITLE: Undoing Track Metadata Changes
STATEMENT: The system shall support undoing track metadata changes.
RELATIONS:
- TYPE: Parent
  VALUE: UR-105

[REQUIREMENT]
UID: SR-126
TITLE: Redoing Track Metadata Changes
STATEMENT: The system shall support redoing track metadata changes.
RELATIONS:
- TYPE: Parent
  VALUE: UR-105

[[/SECTION]]

[[SECTION]]
TITLE: Tags

[REQUIREMENT]
UID: SR-047
TITLE: Creating Tags
STATEMENT: >>>
The system shall allow for the creation tags for use in organising audio files,
playlists and collections.
<<<
RELATIONS:
- TYPE: Parent
  VALUE: UR-022

[REQUIREMENT]
UID: SR-048
TITLE: Deleting Tags
STATEMENT: The system shall allow for the deletion of tags.
RELATIONS:
- TYPE: Parent
  VALUE: UR-022

[REQUIREMENT]
UID: SR-049
TITLE: Removing Deleted Tags
STATEMENT: >>>
The system shall remove deleted tags from any audio files, playlists
or collections that are using them.
<<<
RELATIONS:
- TYPE: Parent
  VALUE: UR-022

[REQUIREMENT]
UID: SR-133
TITLE: Undoing Tag Changes
STATEMENT: >>>
The system shall support undoing playlist and collection metadata changes, 
provided the previous state can be restored.
<<<
RELATIONS:
- TYPE: Parent
  VALUE: UR-082

[REQUIREMENT]
UID: SR-134
TITLE: Redoing Tag Changes
STATEMENT: >>>
The system shall support redoing playlist and collection metadata changes, 
provided the previous state can be restored.
<<<
RELATIONS:
- TYPE: Parent
  VALUE: UR-083

[REQUIREMENT]
UID: SR-050
TITLE: Tag Persistence
STATEMENT: >>>
The system shall preserve tags and their assignments across application sessions.
<<<
RELATIONS:
- TYPE: Parent
  VALUE: UR-022

[[/SECTION]]

[[/SECTION]]

[[SECTION]]
TITLE: Audio Library

[[SECTION]]
TITLE: Adding Local Files

[REQUIREMENT]
UID: SR-051
TITLE: Local Audio File Selection
STATEMENT: >>>
The system shall allow for selected local audio files to be added to the library.
<<<
RELATIONS:
- TYPE: Parent
  VALUE: UR-017

[REQUIREMENT]
UID: SR-052
TITLE: Adding Local Audio Files
STATEMENT: >>>
The system shall add selected supported local audio files to the library.
<<<
RELATIONS:
- TYPE: Parent
  VALUE: UR-017

[REQUIREMENT]
UID: SR-053
TITLE: Handling Inaccessible Local Files
STATEMENT: >>>
The system shall report an error when a selected local audio file cannot be 
accessed or added to the library.
<<<
RELATIONS:
- TYPE: Parent
  VALUE: UR-017

[[/SECTION]]

[[SECTION]]
TITLE: Adding Remote Files

[REQUIREMENT]
UID: SR-054
TITLE: Remote Audio File Selection
STATEMENT: >>>
The system shall allow for selected audio files from connected cloud storage 
providers to be added to the library.
<<<
RELATIONS:
- TYPE: Parent
  VALUE: UR-018

[REQUIREMENT]
UID: SR-055
TITLE: Adding Remote Audio Files
STATEMENT: >>>
The system shall add selected supported remote audio files to the library.
<<<
RELATIONS:
- TYPE: Parent
  VALUE: UR-018

[REQUIREMENT]
UID: SR-056
TITLE: Handling Inaccessible Remote Files
STATEMENT: >>>
The system shall report an error when a selected remote audio file cannot be 
accessed or added to the library.
<<<
RELATIONS:
- TYPE: Parent
  VALUE: UR-017

[[/SECTION]]

[[SECTION]]
TITLE: Removing Files

[REQUIREMENT]
UID: SR-057
TITLE: Preserving Source Audio Files
STATEMENT: >>>
The system shall allow for the removal of a audio files from the library without 
deleting the underlying audio file.
<<<
RELATIONS:
- TYPE: Parent
  VALUE: UR-019

[REQUIREMENT]
UID: SR-058
TITLE: Deleting Source Audio Files
STATEMENT: >>>
The system shall allow for the deletion of a audio files from the underlying 
storage.
<<<
RELATIONS:
- TYPE: Parent
  VALUE: UR-019

[[/SECTION]]

[[SECTION]]
TITLE: Browsing Files

[REQUIREMENT]
UID: SR-059
TITLE: Library Browsing
STATEMENT: >>>
The system shall present the audio files in the library for
browsing and selection.
<<<
RELATIONS:
- TYPE: Parent
  VALUE: UR-020

[REQUIREMENT]
UID: SR-060
TITLE: Library Persistence
STATEMENT: >>>
The system shall preserve library entries across application sessions.
<<<
RELATIONS:
- TYPE: Parent
  VALUE: UR-104

[REQUIREMENT]
UID: SR-061
TITLE: Handling Unavailable Library Files
STATEMENT: >>>
The system shall retain library entries when their associated audio 
files become unavailable.
<<<
RELATIONS:
- TYPE: Parent
  VALUE: UR-104

[REQUIREMENT]
UID: SR-062
TITLE: Differentiating Unavailable Library Files
STATEMENT: >>>
The system shall differentiate unavailable audio files from available audio files.
<<<
RELATIONS:
- TYPE: Parent
  VALUE: UR-104

[[/SECTION]]

[[SECTION]]
TITLE: Undoing and Redoing Actions

[REQUIREMENT]
UID: SR-131
TITLE: Undoing Library Changes
STATEMENT: >>>
The system shall support undoing library changes, provided the 
previous state can be restored.
<<<
RELATIONS:
- TYPE: Parent
  VALUE: UR-021

[REQUIREMENT]
UID: SR-132
TITLE: Redoing Library Changes
STATEMENT: >>>
The system shall support redoing library changes, provided 
the previous state can be restored.
<<<
RELATIONS:
- TYPE: Parent
  VALUE: UR-021

[[/SECTION]]

[[SECTION]]
TITLE: Searching, Sorting, Filtering and Tagging

[REQUIREMENT]
UID: SR-063
TITLE: Removing Tags from Audio Files
STATEMENT: >>>
The system shall allow for the removal of tag assignments from audio files in 
the library without deleting the tags themselves.
<<<
RELATIONS:
- TYPE: Parent
  VALUE: UR-022

[REQUIREMENT]
UID: SR-064
TITLE: Assigning Tags to Audio Files
STATEMENT: >>>
The system shall allow for existing tags to be assigned to audio files in 
the library.
<<<
RELATIONS:
- TYPE: Parent
  VALUE: UR-022

[REQUIREMENT]
UID: SR-065
TITLE: Searching Library Tracks
STATEMENT: >>>
The system shall allow for the searching of tracks in the library using tags or 
supported track attributes.
<<<
RELATIONS:
- TYPE: Parent
  VALUE: UR-023

[REQUIREMENT]
UID: SR-066
TITLE: Empty Search Results
STATEMENT: >>>
The system shall indicate when a library search returns no matching tracks.
<<<
RELATIONS:
- TYPE: Parent
  VALUE: UR-026

[REQUIREMENT]
UID: SR-067
TITLE: Sorting Library Tracks
STATEMENT: >>>
The system shall allow the user to sort library tracks by supported track attributes.
<<<
RELATIONS:
- TYPE: Parent
  VALUE: UR-024

[REQUIREMENT]
UID: SR-068
TITLE: Filtering Library Tracks
STATEMENT: >>>
The system shall allow the user to filter library tracks using supported track 
attributes.
<<<
RELATIONS:
- TYPE: Parent
  VALUE: UR-025

[REQUIREMENT]
UID: SR-069
TITLE: Empty Filter Results
STATEMENT: >>>
The system shall indicate when filtering the library returns no matching tracks.
<<<
RELATIONS:
- TYPE: Parent
  VALUE: UR-026

[[/SECTION]]

[[/SECTION]]

[[SECTION]]
TITLE: Playlists and Collections

[[SECTION]]
TITLE: Playlist Modification

[REQUIREMENT]
UID: SR-070
TITLE: Creating Playlists
STATEMENT: >>>
The system shall allow for the creation of playlists.
<<<
RELATIONS:
- TYPE: Parent
  VALUE: UR-031

[REQUIREMENT]
UID: SR-071
TITLE: Adding Tracks to Playlists
STATEMENT: >>>
The system shall allow for the addition of tracks from the library to a playlist.
<<<
RELATIONS:
- TYPE: Parent
  VALUE: UR-032

[REQUIREMENT]
UID: SR-072
TITLE: Duplicate Playlist Entries
STATEMENT: >>>
The system shall allow the same track to appear multiple times within a playlist.
<<<
RELATIONS:
- TYPE: Parent
  VALUE: UR-032

[REQUIREMENT]
UID: SR-073
TITLE: Removing Tracks from Playlists
STATEMENT: >>>
The system shall allow the user to remove individual track entries from a 
playlist without removing the corresponding tracks from their library.
<<<
RELATIONS:
- TYPE: Parent
  VALUE: UR-033

[REQUIREMENT]
UID: SR-074
TITLE: Modifying Playlist Metadata
STATEMENT: >>>
The system shall allow the user to modify editable metadata fields for playlists.
<<<
RELATIONS:
- TYPE: Parent
  VALUE: UR-035

[REQUIREMENT]
UID: SR-075
TITLE: Persisting Playlists
STATEMENT: >>>
The system shall preserve playlists, including their membership, ordering and 
editable metadata, across application sessions.
<<<
RELATIONS:
- TYPE: Parent
  VALUE: UR-036

[[/SECTION]]

[[SECTION]]
TITLE: Collection Modification

[REQUIREMENT]
UID: SR-076
TITLE: Creating Playlists
STATEMENT: The system shall allow for the creation of collections.
RELATIONS:
- TYPE: Parent
  VALUE: UR-031

[REQUIREMENT]
UID: SR-077
TITLE: Adding Playlists and Collections to Collections
STATEMENT: >>>
The system shall allow the user to add playlists and collections to a collection.
<<<
RELATIONS:
- TYPE: Parent
  VALUE: UR-032

[REQUIREMENT]
UID: SR-078
TITLE: Preventing Circular Collections
STATEMENT: >>>
The system shall prevent the addition of a collection to itself or to any of its 
descendant collections.
<<<

[REQUIREMENT]
UID: SR-079
TITLE: Removing Items from Collections
STATEMENT: >>>
The system shall allow the user to remove playlists and collections from a 
collection without deleting the referenced playlists or collections.
<<<
RELATIONS:
- TYPE: Parent
  VALUE: UR-033

[REQUIREMENT]
UID: SR-080
TITLE: Modifying Collection Metadata
STATEMENT: >>>
The system shall allow the user to modify editable metadata fields for collections.
<<<
RELATIONS:
- TYPE: Parent
  VALUE: UR-035

[REQUIREMENT]
UID: SR-081
TITLE: Persisting Playlists and Collections
STATEMENT: >>>
The system shall preserve collections, including their membership, ordering and 
editable metadata, across application sessions.
<<<
RELATIONS:
- TYPE: Parent
  VALUE: UR-036

[[/SECTION]]

[[SECTION]]
TITLE: Undoing and Redoing Actions

[REQUIREMENT]
UID: SR-82
TITLE: Undoing Playlist and Collection Changes
STATEMENT: >>>
The system shall support undoing playlist and collection changes, provided the 
previous state can be restored.
<<<
RELATIONS:
- TYPE: Parent
  VALUE: UR-102

[REQUIREMENT]
UID: SR-83
TITLE: Redoing Playlist and Collection Changes
STATEMENT: >>>
The system shall support redoing playlist and collection changes, provided 
the previous state can be restored.
<<<
RELATIONS:
- TYPE: Parent
  VALUE: UR-102

[REQUIREMENT]
UID: SR-84
TITLE: Undoing Playlist and Collection Metadata Changes
STATEMENT: >>>
The system shall support undoing playlist and collection metadata changes, 
provided the previous state can be restored.
<<<
RELATIONS:
- TYPE: Parent
  VALUE: UR-103

[REQUIREMENT]
UID: SR-85
TITLE: Redoing Playlist and Collection Metadata Changes
STATEMENT: >>>
The system shall support redoing playlist and collection metadata changes, 
provided the previous state can be restored.
<<<
RELATIONS:
- TYPE: Parent
  VALUE: UR-103

[[/SECTION]]

[[SECTION]]
TITLE: Searching, Sorting, Filtering and Tagging

[REQUIREMENT]
UID: SR-086
TITLE: Removing Tags from Audio Files
STATEMENT: >>>
The system shall allow for the removal of tag assignments from audio files in 
a playlist without deleting the tags themselves.
<<<
RELATIONS:
- TYPE: Parent
  VALUE: UR-037

[REQUIREMENT]
UID: SR-087
TITLE: Removing Tags from playlists and collections 
STATEMENT: >>>
The system shall allow for the removal of tag assignments from a playlist or 
collection without deleting the tags themselves.
<<<
RELATIONS:
- TYPE: Parent
  VALUE: UR-037

[REQUIREMENT]
UID: SR-088
TITLE: Assigning Tags to Audio Files
STATEMENT: >>>
The system shall allow for existing tags to be assigned to audio files in 
a playlist.
<<<
RELATIONS:
- TYPE: Parent
  VALUE: UR-037

[REQUIREMENT]
UID: SR-089
TITLE: Assigning Tags to playlists and collections
STATEMENT: >>>
The system shall allow for existing tags to be assigned to playlists and
collections.
<<<
RELATIONS:
- TYPE: Parent
  VALUE: UR-037

[REQUIREMENT]
UID: SR-090
TITLE: Searching Playlist Tracks
STATEMENT: >>>
The system shall allow for the searching of tracks in a playlist using tags or 
supported track attributes.
<<<
RELATIONS:
- TYPE: Parent
  VALUE: UR-038

[REQUIREMENT]
UID: SR-091
TITLE: Searching Collections for Playlists
STATEMENT: >>>
The system shall allow for the searching of playlists in a collection using 
tags or supported attributes.
<<<
RELATIONS:
- TYPE: Parent
  VALUE: UR-038

[REQUIREMENT]
UID: SR-092
TITLE: Searching Collections for Collections
STATEMENT: >>>
The system shall allow for the searching of collections in a collection using 
tags or supported attributes.
<<<
RELATIONS:
- TYPE: Parent
  VALUE: UR-038

[REQUIREMENT]
UID: SR-093
TITLE: Empty Search Results
STATEMENT: >>>
The system shall indicate when a playlist or collection search returns no 
matching tracks.
<<<
RELATIONS:
- TYPE: Parent
  VALUE: UR-041

[REQUIREMENT]
UID: SR-094
TITLE: Sorting Playlist Tracks
STATEMENT: >>>
The system shall allow the user to sort playlist tracks using supported track 
attributes.
<<<
RELATIONS:
- TYPE: Parent
  VALUE: UR-039

[REQUIREMENT]
UID: SR-095
TITLE: Sorting Collection Playlists and Collections
STATEMENT: >>>
The system shall allow the user to sort playlists and collections inside of a 
collection using supported attributes.
<<<
RELATIONS:
- TYPE: Parent
  VALUE: UR-039

[REQUIREMENT]
UID: SR-096
TITLE: Filtering Playlist Tracks
STATEMENT: >>>
The system shall allow the user to filter playlist tracks using supported track 
attributes.
<<<
RELATIONS:
- TYPE: Parent
  VALUE: UR-025

[REQUIREMENT]
UID: SR-097
TITLE: Filtering Playlists in a Collection
STATEMENT: >>>
The system shall allow the user to filter playlists in a collection using 
supported attributes.
<<<
RELATIONS:
- TYPE: Parent
  VALUE: UR-040

[REQUIREMENT]
UID: SR-098
TITLE: Filtering Collections in a Collection
STATEMENT: >>>
The system shall allow the user to filter collections in a collection using 
supported attributes.
<<<
RELATIONS:
- TYPE: Parent
  VALUE: UR-040

[REQUIREMENT]
UID: SR-099
TITLE: Empty Filter Results
STATEMENT: >>>
The system shall indicate when filtering a playlist or a collection returns no 
matching tracks.
<<<
RELATIONS:
- TYPE: Parent
  VALUE: UR-041

[[/SECTION]]

[[/SECTION]]

[[SECTION]]
TITLE: Queues

[[SECTION]]
TITLE: Queue Viewing and Selection

[REQUIREMENT]
UID: SR-100
TITLE: Viewing Playback Queue
STATEMENT: >>>
The system shall allow the user to view available playback decks and their 
associated queues.
<<<
RELATIONS:
- TYPE: Parent
  VALUE: UR-042

[REQUIREMENT]
UID: SR-101
TITLE: Identifying Active Playback Decks
STATEMENT: >>>
The system shall distinguish playback decks that are currently playing audio 
from decks that are not playing audio.
<<<
RELATIONS:
- TYPE: Parent
  VALUE: UR-043

[REQUIREMENT]
UID: SR-102
TITLE: Selecting Playback Queues
STATEMENT: >>>
The system shall allow the user to associate a playback queue for association with 
a playback deck.
<<<
RELATIONS:
- TYPE: Parent
  VALUE: UR-044

[[/SECTION]]

[[SECTION]]
TITLE: Queue Creation and Management

[REQUIREMENT]
UID: SR-103
TITLE: Creating Playback Queues
STATEMENT: The system shall allow the user to create playback queues.
RELATIONS:
- TYPE: Parent
  VALUE: UR-045

[REQUIREMENT]
UID: SR-104
TITLE: Deleting Playback Queues
STATEMENT: >>>
The system shall allow the user to delete playback queues without deleting 
the tracks in their library.
<<<
RELATIONS:
- TYPE: Parent
  VALUE: UR-045

[REQUIREMENT]
UID: SR-105
TITLE: Adding Tracks to Playback Queues
STATEMENT: >>>
The system shall allow the user to add tracks from their library to playback queues.
<<<
RELATIONS:
- TYPE: Parent
  VALUE: UR-046

[REQUIREMENT]
UID: SR-106
TITLE: Removing Tracks from Playback Queues
STATEMENT: >>>
The system shall allow the user to remove individual track entries from 
playback queues without removing the corresponding tracks from their library.
<<<
RELATIONS:
- TYPE: Parent
  VALUE: UR-046

[REQUIREMENT]
UID: SR-107
TITLE: Reordering Playback Queue Entries
STATEMENT: >>>
The system shall allow the user to change the order of track entries within a 
playback queue.
<<<
RELATIONS:
- TYPE: Parent
  VALUE: UR-047

[[/SECTION]]

[[SECTION]]
TITLE: Undoing and Redoing Actions

[REQUIREMENT]
UID: SR-108
TITLE: Undoing Playback Queue Changes
STATEMENT: >>>
The system shall support undoing playback queue changes, provided the previous
state can be restored.
<<<
RELATIONS:
- TYPE: Parent
  VALUE: UR-048

[REQUIREMENT]
UID: SR-109
TITLE: Redoing Playback Queue Changes
STATEMENT: >>>
The system shall support redoing playback queue changes, provided the previous
state can be restored.
<<<
RELATIONS:
- TYPE: Parent
  VALUE: UR-048

[[/SECTION]]

[[SECTION]]
TITLE: Independent Deck Playback

[REQUIREMENT]
UID: SR-110
TITLE: Independent Playback Deck Control
STATEMENT: >>>
The system shall allow the playback state of each deck to be controlled 
independently of other decks.
<<<
RELATIONS:
- TYPE: Parent
  VALUE: UR-049

[REQUIREMENT]
UID: SR-111
TITLE: Independent Playback Position
STATEMENT: >>>
The system shall allow the playback position of each deck to be adjusted 
independently of other decks.
<<<
RELATIONS:
- TYPE: Parent
  VALUE: UR-049

[REQUIREMENT]
UID: SR-112
TITLE: Independent Playback Volume
STATEMENT: >>>
The system shall allow the playback volume of each deck to be adjusted independently of other decks.
<<<
RELATIONS:
- TYPE: Parent
  VALUE: UR-049

[REQUIREMENT]
UID: SR-113
TITLE: Independent Playback Speed
STATEMENT: >>>
The system shall allow the playback speed of each deck to be adjusted independently of other decks.
<<<
RELATIONS:
- TYPE: Parent
  VALUE: UR-049

[REQUIREMENT]
UID: SR-114
TITLE: Independent Playback Pitch
STATEMENT: >>>
The system shall allow the playback pitch of each deck to be adjusted independently of other decks.
<<<
RELATIONS:
- TYPE: Parent
  VALUE: UR-049

[REQUIREMENT]
UID: SR-115
TITLE: Simultaneous Playback Decks
STATEMENT: >>>
The system shall support simultaneous audio playback on at least two playback decks.
<<<
RELATIONS:
- TYPE: Parent
  VALUE: UR-050

[REQUIREMENT]
UID: SR-116
TITLE: Configuring Queue Switching Behaviour
STATEMENT: >>>
The system shall allow the user to configure the behaviour of a playback deck 
when a different playback queue is associated with it during playback.
<<<
RELATIONS:
- TYPE: Parent
  VALUE: UR-051

[[/SECTION]]

[[SECTION]]
TITLE: Searching, Sorting, Filtering and Tagging

[REQUIREMENT]
UID: SR-117
TITLE: Removing Tags from Audio Files
STATEMENT: >>>
The system shall allow for the removal of tag assignments from audio files in 
a queue without deleting the tags themselves.
<<<
RELATIONS:
- TYPE: Parent
  VALUE: UR-052

[REQUIREMENT]
UID: SR-118
TITLE: Assigning Tags to Audio Files
STATEMENT: >>>
The system shall allow for existing tags to be assigned to audio files in 
a queue.
<<<
RELATIONS:
- TYPE: Parent
  VALUE: UR-052

[REQUIREMENT]
UID: SR-119
TITLE: Searching Queue Tracks
STATEMENT: >>>
The system shall allow for the searching of tracks in a queue using tags or 
supported track attributes.
<<<
RELATIONS:
- TYPE: Parent
  VALUE: UR-053

[REQUIREMENT]
UID: SR-120
TITLE: Empty Search Results
STATEMENT: >>>
The system shall indicate when a queue search returns no matching tracks.
<<<
RELATIONS:
- TYPE: Parent
  VALUE: UR-056

[REQUIREMENT]
UID: SR-121
TITLE: Sorting Queue Tracks
STATEMENT: >>>
The system shall allow the user to sort tracks in a queue using supported track 
attributes.
<<<
RELATIONS:
- TYPE: Parent
  VALUE: UR-054

[REQUIREMENT]
UID: SR-122
TITLE: Filtering Queue Tracks
STATEMENT: >>>
The system shall allow the user to filter tracks in a queue using supported
track attributes.
<<<
RELATIONS:
- TYPE: Parent
  VALUE: UR-055

[REQUIREMENT]
UID: SR-123
TITLE: Empty Filter Results
STATEMENT: >>>
The system shall indicate when filtering a queue returns no matching tracks.
<<<
RELATIONS:
- TYPE: Parent
  VALUE: UR-056

[[/SECTION]]

[[/SECTION]]

[[SECTION]]
TITLE: Data Management

[[SECTION]]
TITLE: Undoing and Redoing Actions

[REQUIREMENT]
UID: SR-172
TITLE: Maintain Action History
STATEMENT: >>>
The system shall maintain a record of actions performed during the current 
session that are relevant to undo and redo operations.
<<<
RELATIONS:
- TYPE: Parent
  VALUE: UR-084

[REQUIREMENT]
UID: SR-173
TITLE: Provide Action History
STATEMENT: >>>
The system shall provide the user with access to the action history for the 
current session.
<<<
RELATIONS:
- TYPE: Parent
  VALUE: UR-084

[REQUIREMENT]
UID: SR-174
TITLE: Identify Undoable Actions
STATEMENT: >>>
The system shall identify actions in the current action history that can 
currently be undone.
<<<
RELATIONS:
- TYPE: Parent
  VALUE: UR-085

[REQUIREMENT]
UID: SR-175
TITLE: Identify Redoable Actions
STATEMENT: >>>
The system shall identify actions in the current action history that can 
currently be redone.
<<<
RELATIONS:
- TYPE: Parent
  VALUE: UR-085

[[/SECTION]]

[[SECTION]]
TITLE: Importing and Exporting User Data

[REQUIREMENT]
UID: SR-200
TITLE: Export Playlists
STATEMENT: >>>
The system shall support exporting playlists and their associated track references.
<<<
RELATIONS:
- TYPE: Parent
  VALUE: UR-087

[REQUIREMENT]
UID: SR-201
TITLE: Export Collections
STATEMENT: >>>
The system shall support exporting collections and their associated contents.
<<<
RELATIONS:
- TYPE: Parent
  VALUE: UR-087

[REQUIREMENT]
UID: SR-202
TITLE: Export Tags
STATEMENT: >>>
The system shall support exporting user-defined tags and their associations 
with tracks.
<<<
RELATIONS:
- TYPE: Parent
  VALUE: UR-087

[REQUIREMENT]
UID: SR-203
TITLE: Export Playback Queues
STATEMENT: >>>
The system shall support exporting playback queues and their associated track 
references in queue order.
<<<
RELATIONS:
- TYPE: Parent
  VALUE: UR-087

[REQUIREMENT]
UID: SR-204
TITLE: Export Track Metadata
STATEMENT: >>>
The system shall support exporting user-created and user-modified track metadata.
<<<
RELATIONS:
- TYPE: Parent
  VALUE: UR-087

[REQUIREMENT]
UID: SR-205
TITLE: Export Preference Configurations
STATEMENT: >>>
The system shall support exporting Configured Preferences.
<<<
RELATIONS:
- TYPE: Parent
  VALUE: UR-087

[REQUIREMENT]
UID: SR-206
TITLE: Export Lyrics
STATEMENT: >>>
The system shall support exporting lyrics associated with tracks, including 
their synchronisation information and language where available.
<<<
RELATIONS:
- TYPE: Parent
  VALUE: UR-087

[REQUIREMENT]
UID: SR-207
TITLE: Exclude Audio Content from Exports
STATEMENT: >>>
The system shall not include audio content from source tracks in exported 
user-created information.
<<<
RELATIONS:
- TYPE: Parent
  VALUE: UR-087

[REQUIREMENT]
UID: SR-208
TITLE: Import Playlists
STATEMENT: >>>
The system shall support importing playlists and their associated track references.
<<<
RELATIONS:
- TYPE: Parent
  VALUE: UR-086

[REQUIREMENT]
UID: SR-209
TITLE: Import Collections
STATEMENT: The system shall support importing collections and their associated contents.
RELATIONS:
- TYPE: Parent
  VALUE: UR-086

[REQUIREMENT]
UID: SR-210
TITLE: Import Tags
STATEMENT: The system shall support importing user-defined tags and their associations with tracks.
RELATIONS:
- TYPE: Parent
  VALUE: UR-086

[REQUIREMENT]
UID: SR-211
TITLE: Import Playback Queues
STATEMENT: The system shall support importing playback queues and their associated track references in queue order.
RELATIONS:
- TYPE: Parent
  VALUE: UR-086

[REQUIREMENT]
UID: SR-212
TITLE: Import Track Metadata
STATEMENT: The system shall support importing track metadata.
RELATIONS:
- TYPE: Parent
  VALUE: UR-086

[REQUIREMENT]
UID: SR-213
TITLE: Export Preference Configurations
STATEMENT: >>>
The system shall support exporting Configured Preferences.
<<<
RELATIONS:
- TYPE: Parent
  VALUE: UR-087

[REQUIREMENT]
UID: SR-214
TITLE: Import Lyrics
STATEMENT: >>>
The system shall support importing lyrics associated with tracks, including 
their synchronisation information and language where available.
<<<
RELATIONS:
- TYPE: Parent
  VALUE: UR-086

[REQUIREMENT]
UID: SR-215
TITLE: Selecting Shared Information Categories
STATEMENT: >>>
The system shall support the selection of supported categories for user-created 
information to import or export.
<<<
RELATIONS:
- TYPE: Parent
  VALUE: UR-106

[[/SECTION]]

[[/SECTION]]

[[SECTION]]
TITLE: Library Analitics

[[SECTION]]
TITLE: Library Activity Recording

[REQUIREMENT]
UID: SR-216
TITLE: Record Library Activity
STATEMENT: >>>
The system shall record supported library activities.
<<<
RELATIONS:
- TYPE: Parent
  VALUE: UR-066

[REQUIREMENT]
UID: SR-217
TITLE: Record Library Activity
STATEMENT: >>>
The system shall record supported library activities.
<<<
RELATIONS:
- TYPE: Parent
  VALUE: UR-066

[REQUIREMENT]
UID: SR-218
TITLE: Record Library Activity
STATEMENT: >>>
The system shall record supported library activities.
<<<
RELATIONS:
- TYPE: Parent
  VALUE: UR-066

[REQUIREMENT]
UID: SR-219
TITLE: Record Library Activity
STATEMENT: >>>
The system shall record supported library activities.
<<<
RELATIONS:
- TYPE: Parent
  VALUE: UR-066

[[/SECTION]]

[[SECTION]]
TITLE: Deleting Library History

[REQUIREMENT]
UID: SR-300
TITLE: Deleting Library Activity
STATEMENT: >>>
The system shall support deleting recorded library activity information.
<<<
RELATIONS:
- TYPE: Parent
  VALUE: UR-067

[REQUIREMENT]
UID: SR-301
TITLE: Deleting Historical Library Activity
STATEMENT: >>>
The system shall support deleting recorded library activity information for 
specified historical time periods.
<<<
RELATIONS:
- TYPE: Parent
  VALUE: UR-067

[[/SECTION]]

[[SECTION]]
TITLE: Library Activity Review

[REQUIREMENT]
UID: SR-302
TITLE: Retrieving Historical Library Activity
STATEMENT: >>>
The system shall support retrieving recorded library activity information for 
specified historical time periods.
<<<
RELATIONS:
- TYPE: Parent
  VALUE: UR-068

[REQUIREMENT]
UID: SR-303
TITLE: Filtering Historical Library Activity
STATEMENT: >>>
The system shall support filtering recorded library activity information for 
specified historical time periods.
<<<
RELATIONS:
- TYPE: Parent
  VALUE: UR-068

[REQUIREMENT]
UID: SR-304
TITLE: Sorting Historical Library Activity
STATEMENT: >>>
The system shall support sorting recorded library activity information for specified 
historical time periods.
<<<
RELATIONS:
- TYPE: Parent
  VALUE: UR-068

[[/SECTION]]

[[SECTION]]
TITLE: Library Activity Analysis

[REQUIREMENT]
UID: SR-305
TITLE: Analysing Historical Library Activity
STATEMENT: >>>
The system shall support analysing recorded library activity information for 
specified historical time periods.
<<<
RELATIONS:
- TYPE: Parent
  VALUE: UR-069

[REQUIREMENT]
UID: SR-306
TITLE: Calculating Library Activity Statistics
STATEMENT: >>>
The system shall calculate statistical measurements from recorded library activity.
<<<
RELATIONS:
- TYPE: Parent
  VALUE: UR-069

[REQUIREMENT]
UID: SR-307
TITLE: Comparing Library Activity Behaviour
STATEMENT: >>>
The system shall support comparing library activity statistics across different
historical time periods.
<<<
RELATIONS:
- TYPE: Parent
  VALUE: UR-069

[[/SECTION]]

[[/SECTION]]

[[SECTION]]
TITLE: Listening Analytics

[[SECTION]]
TITLE: Listening Activity Recording

[REQUIREMENT]
UID: SR-220
TITLE: Record Listening Activity
STATEMENT: The system shall record supported listening activities.
RELATIONS:
- TYPE: Parent
  VALUE: UR-070

[REQUIREMENT]
UID: SR-221
TITLE: Record Track Playback
STATEMENT: >>>
The system shall record track playback events, including the associated track 
and occurence timestamp.
<<<
RELATIONS:
- TYPE: Parent
  VALUE: UR-070

[REQUIREMENT]
UID: SR-222
TITLE: Record Listening Duration
STATEMENT: >>>
The system shall maintain a record of listening activity for subsequent retrieval.
<<<
RELATIONS:
- TYPE: Parent
  VALUE: UR-070

[[/SECTION]]

[[SECTION]]
TITLE: Listening History Management

[REQUIREMENT]
UID: SR-223
TITLE: Retrieve Listening History
STATEMENT: >>>
The system shall support toggling whether to record available listening analytics.
<<<
RELATIONS:
- TYPE: Parent
  VALUE: UR-070

[REQUIREMENT]
UID: SR-224
TITLE: Retrieve Listening History
STATEMENT: The system shall support retrieving recorded listening history.
RELATIONS:
- TYPE: Parent
  VALUE: UR-070

[REQUIREMENT]
UID: SR-225
TITLE: Delete Listening History
STATEMENT: The system shall support deleting recorded listening history.
RELATIONS:
- TYPE: Parent
  VALUE: UR-071

[REQUIREMENT]
UID: SR-226
TITLE: Delete Historical Listening Activity
STATEMENT: >>>
The system shall support deleting recorded listening history for specified 
historical time periods.
<<<
RELATIONS:
- TYPE: Parent
  VALUE: UR-071

[[/SECTION]]

[[SECTION]]
TITLE: Historical Listening Review

[REQUIREMENT]
UID: SR-227
TITLE: Retrieve Historical Listening Activity
STATEMENT: >>>
The system shall support retrieving listening history for specified historical 
time periods.
<<<
RELATIONS:
- TYPE: Parent
  VALUE: UR-072

[REQUIREMENT]
UID: SR-228
TITLE: Filter Listening History
STATEMENT: >>>
The system shall support filtering listening history by supported track 
attributes and playback information.
<<<
RELATIONS:
- TYPE: Parent
  VALUE: UR-072

[REQUIREMENT]
UID: SR-229
TITLE: Sort Listening History
STATEMENT: The system shall support sorting listening history chronologically.
RELATIONS:
- TYPE: Parent
  VALUE: UR-072

[[/SECTION]]

[[SECTION]]
TITLE: Listening Behaviour Analysis

[REQUIREMENT]
UID: SR-230
TITLE: Analyse Listening Behaviour
STATEMENT: >>>
The system shall support analysing recorded listening activity over specific
historical time periods.
<<<
RELATIONS:
- TYPE: Parent
  VALUE: UR-073

[REQUIREMENT]
UID: SR-231
TITLE: Calculate Listening Statistics
STATEMENT: >>>
The system shall calculate statistical measurements from recorded listening 
activity.
<<<
RELATIONS:
- TYPE: Parent
  VALUE: UR-073

[REQUIREMENT]
UID: SR-232
TITLE: Analyse Listening Behaviour
STATEMENT: >>>
The system shall support comparing listening statistics across different
historical time periods.
<<<
RELATIONS:
- TYPE: Parent
  VALUE: UR-073

[TEXT]
STATEMENT: >>>
Note that statistics includes but is not limited to: 
Play counts and listening duration per track/artist/album
Listening distribution by genre/language
Listening behaviour by time of day and day of week
Track completion and skip rates
Most frequently played tracks over a period
<<<

[[/SECTION]]

[[/SECTION]]

[[SECTION]]
TITLE: Settings

[[SECTION]]
TITLE: Preferences

[[/SECTION]]

[[SECTION]]
TITLE: Internationalisation

[REQUIREMENT]
UID: SR-270
TITLE: Provide Available Languages
STATEMENT: >>>
The system shall provide a list of languages available for application use.
<<<
RELATIONS:
- TYPE: Parent
  VALUE: UR-061

[REQUIREMENT]
UID: SR-271
TITLE: Identify Installed Languages
STATEMENT: >>>
The system shall identify which application languages are currently installed.
<<<
RELATIONS:
- TYPE: Parent
  VALUE: UR-061

[REQUIREMENT]
UID: SR-272
TITLE: Identify Default Language
STATEMENT: >>>
The system shall identify the default application language.
<<<
RELATIONS:
- TYPE: Parent
  VALUE: UR-061

[REQUIREMENT]
UID: SR-273
TITLE: Preview Application Languages
STATEMENT: >>>
The system shall support previewing the application in available languages.
<<<
RELATIONS:
- TYPE: Parent
  VALUE: UR-061

[REQUIREMENT]
UID: SR-274
TITLE: Select Application Languages
STATEMENT: >>>
The system shall support selection of an available application language.
<<<
RELATIONS:
- TYPE: Parent
  VALUE: UR-062

[REQUIREMENT]
UID: SR-275
TITLE: Apply Application Languages
STATEMENT: >>>
The system shall display supported application content in the selected language.
<<<
RELATIONS:
- TYPE: Parent
  VALUE: UR-063

[REQUIREMENT]
UID: SR-276
TITLE: Install Application Languages
STATEMENT: >>>
The system shall support installing additional language resources from 
external sources.
<<<
RELATIONS:
- TYPE: Parent
  VALUE: UR-064

[REQUIREMENT]
UID: SR-277
TITLE: Remove Installed Application Languages
STATEMENT: >>>
The system shall support removing language resources if more than one is
installed.
<<<
RELATIONS:
- TYPE: Parent
  VALUE: UR-064

[REQUIREMENT]
UID: SR-278
TITLE: Persist Application Languages
STATEMENT: >>>
The system shall retain the selected application language between application
sessions.
<<<
RELATIONS:
- TYPE: Parent
  VALUE: UR-065

[REQUIREMENT]
UID: SR-279
TITLE: Handle Unavailable Selected Languages
STATEMENT: >>>
The system shall select an available fallback language when the previously
selected language is no longer available.
<<<
RELATIONS:
- TYPE: Parent
  VALUE: UR-065

[[/SECTION]]

[[/SECTION]]

[[SECTION]]
TITLE: User Experience

[[SECTION]]
TITLE: Interface Provision

[REQUIREMENT]
UID: SR-310
TITLE: Provide TUI Interface
STATEMENT: >>>
The system shall provide a text-based user interface through which users can access
supported application functionality.
<<<
RELATIONS:
- TYPE: Parent
  VALUE: UR-077

[REQUIREMENT]
UID: SR-311
TITLE: Provide GUI Interface
STATEMENT: >>>
The system shall provide a graphical user interface through which users can access
supported application functionality.
<<<
RELATIONS:
- TYPE: Parent
  VALUE: UR-078

[[/SECTION]]

[[SECTION]]
TITLE: Control Discoverability

[REQUIREMENT]
UID: SR-312
TITLE: Identify Available Controls
STATEMENT: >>>
The system shall provide information identifying the controls available within 
the active interface.
<<<
RELATIONS:
- TYPE: Parent
  VALUE: UR-079

[REQUIREMENT]
UID: SR-313
TITLE: Provide Control Usage Instructions
STATEMENT: >>>
The system shall provide instructions describing how available controls are used.
<<<
RELATIONS:
- TYPE: Parent
  VALUE: UR-079

[[/SECTION]]

[[SECTION]]
TITLE: Control Customisation

[REQUIREMENT]
UID: SR-314
TITLE: Customise Interface Controls
STATEMENT: >>>
The system shall support customisation of supported interface controls.
<<<
RELATIONS:
- TYPE: Parent
  VALUE: UR-080

[REQUIREMENT]
UID: SR-315
TITLE: Retain Control Customisations
STATEMENT: >>>
The system shall retain configured control customistaions between application 
sessions.
<<<
RELATIONS:
- TYPE: Parent
  VALUE: UR-080

[REQUIREMENT]
UID: SR-316
TITLE: Restore Default Controls
STATEMENT: >>>
The system shall support restoring interface controls to their default 
configurations.
<<<
RELATIONS:
- TYPE: Parent
  VALUE: UR-080

[[/SECTION]]

[[SECTION]]
TITLE: Interactions

[REQUIREMENT]
UID: SR-317
TITLE: Support User Interaction
STATEMENT: >>>
The system shall support user interaction through provided interface controls.
<<<
RELATIONS:
- TYPE: Parent
  VALUE: UR-081

[REQUIREMENT]
UID: SR-318
TITLE: Execute Supported Operations
STATEMENT: >>>
The system shall execute supported operations in response to valid user 
interactions.
<<<
RELATIONS:
- TYPE: Parent
  VALUE: UR-081

[REQUIREMENT]
UID: SR-319
TITLE: Provide Interaction Feedback
STATEMENT: >>>
The system shall provide feedback to users in response to supported interactions.
<<<
RELATIONS:
- TYPE: Parent
  VALUE: UR-081

[[/SECTION]]

[[/SECTION]]

[[SECTION]]
TITLE: Remote Playback Synchronisation

[[SECTION]]
TITLE: Device Discovery and Information

[REQUIREMENT]
UID: SR-350
TITLE: Discover Connected Devices
STATEMENT: >>>
The system shall identify supported devices available for connection.
<<<
RELATIONS:
- TYPE: Parent
  VALUE: UR-075

[REQUIREMENT]
UID: SR-351
TITLE: Identify Connected Devices
STATEMENT: >>>
The system shall maintain information identifying connected devices.
<<<
RELATIONS:
- TYPE: Parent
  VALUE: UR-075

[REQUIREMENT]
UID: SR-352
TITLE: Provide Device Capabilities
STATEMENT: >>>
The system shall provide information about its supported capabilities to 
connected devices.
<<<
RELATIONS:
- TYPE: Parent
  VALUE: UR-075

[REQUIREMENT]
UID: SR-353
TITLE: Retrieve Device Capabilities
STATEMENT: >>>
The system shall retrieve information about the capabilities of connected devices.
<<<
RELATIONS:
- TYPE: Parent
  VALUE: UR-075

[REQUIREMENT]
UID: SR-354
TITLE: Provide System Resource Information
STATEMENT: >>>
The system shall provide permitted information about its available system
resources to connected devices.
<<<
RELATIONS:
- TYPE: Parent
  VALUE: UR-075

[REQUIREMENT]
UID: SR-355
TITLE: Retrieve System Resource Information
STATEMENT: >>>
The system shall retrieve available system resource information from connected
devices.
<<<
RELATIONS:
- TYPE: Parent
  VALUE: UR-075

[REQUIREMENT]
UID: SR-356
TITLE: Update System Resource Information
STATEMENT: >>>
The system shall update advertised system resource information when relevant 
resource availability changes.
<<<
RELATIONS:
- TYPE: Parent
  VALUE: UR-075

[[/SECTION]]

[[SECTION]]
TITLE: Playback Synchronisation

[REQUIREMENT]
UID: SR-357
TITLE: Provide Playback Synchronisation Information
STATEMENT: >>>
The system shall provide playback synchronisation information to connected devices.
<<<
RELATIONS:
- TYPE: Parent
  VALUE: UR-075

[REQUIREMENT]
UID: SR-358
TITLE: Receive Playback Synchronisation Information
STATEMENT: >>>
The system shall receive playback synchronisation information from connected 
devices.
<<<
RELATIONS:
- TYPE: Parent
  VALUE: UR-075

[REQUIREMENT]
UID: SR-359
TITLE: Synchronize Local Playback
STATEMENT: >>>
The system shall synchronise local playback with playback information received 
from a connected device.
<<<
RELATIONS:
- TYPE: Parent
  VALUE: UR-075

[REQUIREMENT]
UID: SR-360
TITLE: Identify Synchronisation Source
STATEMENT: >>>
The system shall identify the connected device providing playback 
synchronisation information.
<<<
RELATIONS:
- TYPE: Parent
  VALUE: UR-075

[REQUIREMENT]
UID: SR-361
TITLE: Handle Synchronization Changes
STATEMENT: >>>
The system shall update local playback in response to relevant changes in the 
synchronisation source's playback state.
<<<
RELATIONS:
- TYPE: Parent
  VALUE: UR-075

[REQUIREMENT]
UID: SR-362
TITLE: Identify Matching Audio Tracks
STATEMENT: >>>
The system shall identify audio tracks across connected devices using supported
track identifiers.
<<<
RELATIONS:
- TYPE: Parent
  VALUE: UR-075

[[/SECTION]]

[[SECTION]]
TITLE: Sharing Permissions

[REQUIREMENT]
UID: SR-363
TITLE: Configure Sharing Permissions
STATEMENT: >>>
The system shall allow sharing permissions to be configured for supported
information and operations.
<<<
RELATIONS:
- TYPE: Parent
  VALUE: UR-075

[REQUIREMENT]
UID: SR-364
TITLE: Configure Device-Specific Sharing Permissions
STATEMENT: >>>
The system shall allow sharing permissions to be configured for individual
connected devices.
<<<
RELATIONS:
- TYPE: Parent
  VALUE: UR-075

[REQUIREMENT]
UID: SR-365
TITLE: Persist Sharing Permissions
STATEMENT: >>>
The system shall retain configured sharing permissions between application sessions.
<<<
RELATIONS:
- TYPE: Parent
  VALUE: UR-075

[[/SECTION]]

[[SECTION]]
TITLE: Authentication and Authorisation

[REQUIREMENT]
UID: SR-366
TITLE: Track Remote Processing Requests
STATEMENT: >>>
The system shall maintain the status of remote lyrics processing requests.
<<<
RELATIONS:
- TYPE: Parent
  VALUE: UR-075

[REQUIREMENT]
UID: SR-367
TITLE: Handle Remote Processing Failures
STATEMENT: >>>
The system shall handle unsuccessful remote lyrics processing requests without
corrupting existing lyrics data.
<<<
RELATIONS:
- TYPE: Parent
  VALUE: UR-075

[REQUIREMENT]
UID: SR-368
TITLE: Handle Device Disconnections
STATEMENT: >>>
The system shall handle the disconnection of devices participating in distributed
operations.
<<<
RELATIONS:
- TYPE: Parent
  VALUE: UR-075

[REQUIREMENT]
UID: SR-369
TITLE: Authenticate Connected Devices
STATEMENT: >>>
The system shall authenticate devices before permitting access to protected
information or operations.
<<<
RELATIONS:
- TYPE: Parent
  VALUE: UR-075

[REQUIREMENT]
UID: SR-370
TITLE: Authorise Remote Operations
STATEMENT: >>>
The system shall verify that connected devices are authorised to perform operations.
<<<
RELATIONS:
- TYPE: Parent
  VALUE: UR-075

[[/SECTION]]

[[/SECTION]]

[[/SECTION]]

[[SECTION]]
TITLE: Lyrics Player

[[SECTION]]
TITLE: View and Modify Lyrics

[REQUIREMENT]
UID: SR-500
TITLE: Retrieve Track Lyrics
STATEMENT: >>>
The system shall support retrieving lyrics associated with an audio track.
<<<
RELATIONS:
- TYPE: Parent
  VALUE: UR-088

[REQUIREMENT]
UID: SR-501
TITLE: Display Track Lyrics
STATEMENT: >>>
The system shall display retrieved lyrics associated with the selected audio track.
<<<
RELATIONS:
- TYPE: Parent
  VALUE: UR-088

[REQUIREMENT]
UID: SR-502
TITLE: Modify Track Lyrics
STATEMENT: >>>
The system shall support modifying lyrics associated with an audio track.
<<<
RELATIONS:
- TYPE: Parent
  VALUE: UR-089

[REQUIREMENT]
UID: SR-503
TITLE: Save Modified Lyrics
STATEMENT: >>>
The system shall retain modifications made to lyrics.
<<<
RELATIONS:
- TYPE: Parent
  VALUE: UR-089

[REQUIREMENT]
UID: SR-504
TITLE: Enable Lyrics Display
STATEMENT: >>>
The system shall support enabling the display of lyrics during playback.
<<<
RELATIONS:
- TYPE: Parent
  VALUE: UR-090

[REQUIREMENT]
UID: SR-505
TITLE: Disable Lyrics Display
STATEMENT: >>>
The system shall support disabling the display of lyrics during playback.
<<<
RELATIONS:
- TYPE: Parent
  VALUE: UR-090

[[/SECTION]]

[[SECTION]]
TITLE: Translate Lyrics

[REQUIREMENT]
UID: SR-506
TITLE: Translate Track Lyrics
STATEMENT: >>>
The system shall support translating lyrics into supported target languages.
<<<
RELATIONS:
- TYPE: Parent
  VALUE: UR-091

[REQUIREMENT]
UID: SR-507
TITLE: Associate Translation with Original Lyrics
STATEMENT: >>>
The system shall associate translated lyrics with their corresponding original 
lyrics and audio track.
<<<
RELATIONS:
- TYPE: Parent
  VALUE: UR-091

[REQUIREMENT]
UID: SR-508
TITLE: Maintain Multiple Lyrics Translations
STATEMENT: >>>
The system shall support maintaining multiple translations of lyrics associated
with an audio track.
<<<
RELATIONS:
- TYPE: Parent
  VALUE: UR-092

[REQUIREMENT]
UID: SR-509
TITLE: Select Lyrics Translation
STATEMENT: >>>
The system shall support selecting an available translation of lyrics for display.
<<<
RELATIONS:
- TYPE: Parent
  VALUE: UR-092

[[/SECTION]]

[[SECTION]]
TITLE: Align Lyrics

[REQUIREMENT]
UID: SR-510
TITLE: Align Lyrics with Audio
STATEMENT: >>>
The system shall support aligning lyrics with their associated audio track.
<<<
RELATIONS:
- TYPE: Parent
  VALUE: UR-093

[REQUIREMENT]
UID: SR-511
TITLE: Maintain Multiple Lyrics Alignments
STATEMENT: >>>
The system shall support maintaining multiple alignments of lyrics associated
with an audio track.
<<<
RELATIONS:
- TYPE: Parent
  VALUE: UR-092

[REQUIREMENT]
UID: SR-512
TITLE: Associate Alignment with Original Lyrics
STATEMENT: >>>
The system shall associate aligned lyrics with their corresponding original 
lyrics and audio track.
<<<
RELATIONS:
- TYPE: Parent
  VALUE: UR-093

[REQUIREMENT]
UID: SR-513
TITLE: Support Multiple Lyrics Alignment Levels
STATEMENT: >>>
The system shall support lyric alignment at multiple levels of granularity.
<<<
RELATIONS:
- TYPE: Parent
  VALUE: UR-093

[REQUIREMENT]
UID: SR-514
TITLE: Select Lyrics Alignment
STATEMENT: >>>
The system shall support selecting an available alignment of lyrics for display.
<<<
RELATIONS:
- TYPE: Parent
  VALUE: UR-094

[[/SECTION]]

[[SECTION]]
TITLE: Download Lyrics

[REQUIREMENT]
UID: SR-515
TITLE: Align Lyrics with Audio
STATEMENT: >>>
The system shall support retrieving lyrics from supported external sources.
<<<
RELATIONS:
- TYPE: Parent
  VALUE: UR-095

[REQUIREMENT]
UID: SR-516
TITLE: Identify Available Lyrics Sources
STATEMENT: >>>
The system shall identify external sources available for retrieving lyrics.
<<<
RELATIONS:
- TYPE: Parent
  VALUE: UR-096

[REQUIREMENT]
UID: SR-517
TITLE: Select Lyrics Download Source
STATEMENT: >>>
The system shall support selecting an available source for retrieving lyrics.
<<<
RELATIONS:
- TYPE: Parent
  VALUE: UR-096

[REQUIREMENT]
UID: SR-518
TITLE: Identify Available Lyric Alignments
STATEMENT: >>>
The system shall identify the alignment levels available for lyrics that are to 
be downloaded if they are retrievable.
<<<
RELATIONS:
- TYPE: Parent
  VALUE: UR-097

[REQUIREMENT]
UID: SR-519
TITLE: Select Lyrics Download Alignment
STATEMENT: >>>
The system shall support selecting the alignment level of lyrics retrieved from 
an external source.
<<<
RELATIONS:
- TYPE: Parent
  VALUE: UR-097

[[/SECTION]]

[[SECTION]]
TITLE: Synchronized Lyrics

[REQUIREMENT]
UID: SR-520
TITLE: Identify Remote Lyrics
STATEMENT: >>>
The system shall identify lyrics associated with matching audio tracks that are 
available on connected devices.
<<<
RELATIONS:
- TYPE: Parent
  VALUE: UR-110

[REQUIREMENT]
UID: SR-521
TITLE: Advertise Available Lyrics
STATEMENT: >>>
The system shall make permitted lyrics available for discovery by connected devices.
<<<
RELATIONS:
- TYPE: Parent
  VALUE: UR-110

[REQUIREMENT]
UID: SR-522
TITLE: Advertise Lyrics Processing Requests
STATEMENT: >>>
The system shall advertise supported lyrics processing operations to connected 
devices.
<<<
RELATIONS:
- TYPE: Parent
  VALUE: UR-110

[REQUIREMENT]
UID: SR-523
TITLE: Provide Lyrics Attributes
STATEMENT: >>>
The system shall provide supported metadata describing available lyrics to 
connected devices.
<<<
RELATIONS:
- TYPE: Parent
  VALUE: UR-110

[REQUIREMENT]
UID: SR-524
TITLE: Execute Remote Lyrics Translation
STATEMENT: >>>
The system shall execute permitted lyrics translation requests received from 
connected devices.
<<<
RELATIONS:
- TYPE: Parent
  VALUE: UR-110

[REQUIREMENT]
UID: SR-525
TITLE: Execute Remote Lyrics Alignment
STATEMENT: >>>
The system shall execute permitted lyrics alignment requests received from 
connected devices.
<<<
RELATIONS:
- TYPE: Parent
  VALUE: UR-110

[REQUIREMENT]
UID: SR-526
TITLE: Return Lyrics Processing Results
STATEMENT: >>>
The system shall return the results of completed lyrics processing requests to 
the requesting device.
<<<
RELATIONS:
- TYPE: Parent
  VALUE: UR-110

[REQUIREMENT]
UID: SR-527
TITLE: Retrieve Remote Lyrics
STATEMENT: >>>
The system shall retrieve a selected lyrics version from its associated connected
device.
<<<
RELATIONS:
- TYPE: Parent
  VALUE: UR-110

[REQUIREMENT]
UID: SR-528
TITLE: Retain Retrieved Lyrics
STATEMENT: The system shall support retaining retrieved lyrics locally.
RELATIONS:
- TYPE: Parent
  VALUE: UR-110

[REQUIREMENT]
UID: SR-529
TITLE: Control Remote Processing Availability
STATEMENT: >>>
The system shall allow remote lyrics processing requests to be enabled and disabled.
<<<
RELATIONS:
- TYPE: Parent
  VALUE: UR-110

[REQUIREMENT]
UID: SR-530
TITLE: Consider Available System Resources
STATEMENT: >>>
The system shall consider available system resources when accepting remote lyrics
processing requests.
<<<
RELATIONS:
- TYPE: Parent
  VALUE: UR-110

[REQUIREMENT]
UID: SR-531
TITLE: Select Lyrics Variants
STATEMENT: >>>
The system shall support the selection of a lyrics variation from the available 
local and remote variations associated with an audio track.
<<<
RELATIONS:
- TYPE: Parent
  VALUE: UR-110

[[/SECTION]]

[[/SECTION]]

[[SECTION]]
TITLE: Audio Visualiser

[[SECTION]]
TITLE: Audio Visualisation Provision

[REQUIREMENT]
UID: SR-600
TITLE: Generate Audio Visualisations
STATEMENT: >>>
The system shall generate visual representations of audio during playback.
<<<
RELATIONS:
- TYPE: Parent
  VALUE: UR-098

[REQUIREMENT]
UID: SR-601
TITLE: Generate Audio Visualisations
STATEMENT: >>>
The system shall display generated audio visualisations through supported 
interfaces.
<<<
RELATIONS:
- TYPE: Parent
  VALUE: UR-098

[REQUIREMENT]
UID: SR-602
TITLE: Generate Audio Visualisations
STATEMENT: >>>
The system shall support multiple audio visualisation types.
<<<
RELATIONS:
- TYPE: Parent
  VALUE: UR-098

[TEXT]
STATEMENT: >>>
Types may include but are not limited to: Waveforms, Spectrums and Spectograms
<<<

[[/SECTION]]

[[SECTION]]
TITLE: Audio Visualisation Customisation

[REQUIREMENT]
UID: SR-603
TITLE: Customise Audio Visualisations
STATEMENT: >>>
The system shall support the customisation of supported audio visualisation 
settings.
<<<
RELATIONS:
- TYPE: Parent
  VALUE: UR-099

[REQUIREMENT]
UID: SR-604
TITLE: Select Audio Visualisation Type
STATEMENT: >>>
The system shall allow the user to select from supported audio visualisation types.
<<<
RELATIONS:
- TYPE: Parent
  VALUE: UR-099

[REQUIREMENT]
UID: SR-605
TITLE: Configure Audio Visualisation Appearance
STATEMENT: >>>
The system shall support configuring the appearance of supported audio 
visualisations.
<<<
RELATIONS:
- TYPE: Parent
  VALUE: UR-099

[REQUIREMENT]
UID: SR-606
TITLE: Configure Audio Visualisation Behaviour
STATEMENT: >>>
The system shall support configuring the behaviour of supported audio 
visualisations.
<<<
RELATIONS:
- TYPE: Parent
  VALUE: UR-099

[[/SECTION]]

[[SECTION]]
TITLE: Enabling and Disabling Audio Visualisations

[REQUIREMENT]
UID: SR-607
TITLE: Enable Audio Visualisation
STATEMENT: >>>
The system shall support enabling audio visualisation during playback.
<<<
RELATIONS:
- TYPE: Parent
  VALUE: UR-100

[REQUIREMENT]
UID: SR-608
TITLE: Disable Audio Visualisation
STATEMENT: >>>
The system shall support disabling audio visualisation during playback.
<<<
RELATIONS:
- TYPE: Parent
  VALUE: UR-100

[REQUIREMENT]
UID: SR-609
TITLE: Maintain Audio Visualisation State
STATEMENT: >>>
The system shall maintain the current enabled or disabled state of audio
visualisation
<<<
RELATIONS:
- TYPE: Parent
  VALUE: UR-100

[[/SECTION]]

[[SECTION]]
TITLE: Audio Visualisation Settings Persistence

[REQUIREMENT]
UID: SR-610
TITLE: Persist Audio Visualisation Settings
STATEMENT: >>>
The system shall retain configured audio visualisation settings between
application sessions.
<<<
RELATIONS:
- TYPE: Parent
  VALUE: UR-101

[REQUIREMENT]
UID: SR-611
TITLE: Restore Audio Visualisation Settings
STATEMENT: >>>
The system shall restore previously configured audio visualisation settings when
starting a new application session.
<<<
RELATIONS:
- TYPE: Parent
  VALUE: UR-101

[[/SECTION]]

[[SECTION]]
TITLE: Synchronized Audio Visualisations

[REQUIREMENT]
UID: SR-650
TITLE: Synchronize Remote Audio Visualisations
STATEMENT: >>>
The system shall enable connected devices to display audio visualisations 
synchronized with the current audio playback.
<<<
RELATIONS:
- TYPE: Parent
  VALUE: UR-120

[[/SECTION]]

[[/SECTION]]
