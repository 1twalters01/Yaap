[DOCUMENT]
TITLE: User Requirements
UID: YAAP-UR
DATE: @GIT_COMMIT_DATETIME
PREFIX: UR-

[[SECTION]]
TITLE: Introduction

[TEXT]
STATEMENT: >>>
This document defines the user requirements for Yet Another Audio Player (Yaap),
a time accurate desktop audio player.
<<<

[[/SECTION]]

[[SECTION]]
TITLE: Audio Playback

[[SECTION]]
TITLE: Supported Audio Playback

[REQUIREMENT]
UID: UR-001
TITLE: Supported Audio Formats
STATEMENT: The user shall be able to play audio tracks in supported audio formats.
RELATIONS:
- TYPE: Parent
  VALUE: BR-001

[REQUIREMENT]
UID: UR-002
TITLE: Unsupported Audio Formats
STATEMENT: The user shall be able to identify audio files that Yaap cannot play.
RELATIONS:
- TYPE: Parent
  VALUE: BR-001

[[/SECTION]]

[[SECTION]]
TITLE: Playing files

[REQUIREMENT]
UID: UR-003
TITLE: Playing local files
STATEMENT: >>>
The user shall be able to play supported audio files stored on their device.
<<<
RELATIONS:
- TYPE: Parent
  VALUE: BR-002

[REQUIREMENT]
UID: UR-004
TITLE: Cloud storage Connections
STATEMENT: >>>
The user shall be able to connect Yaap to supported cloud storage providers.
<<<
RELATIONS:
- TYPE: Parent
  VALUE: BR-003

[REQUIREMENT]
UID: UR-005
TITLE: Playing Remote files
STATEMENT: >>>
The user shall be able to play supported audio files stored with a connected cloud
provider.
<<<
RELATIONS:
- TYPE: Parent
  VALUE: BR-003

[REQUIREMENT]
UID: UR-006
TITLE: Audio Quality
STATEMENT: >>>
The user shall be able to play supported audio tracks at the quality provided 
by the source audio.
<<<
RELATIONS:
- TYPE: Parent
  VALUE: BR-004

[[/SECTION]]

[[SECTION]]
TITLE: Audio Playback Position

[REQUIREMENT]
UID: UR-007
TITLE: View Playback Position
STATEMENT: >>>
The user shall be able to view the current playback position of an audio track.
<<<
RELATIONS:
- TYPE: Parent
  VALUE: BR-005

[REQUIREMENT]
UID: UR-008
TITLE: Elapsed Playback Time
STATEMENT: >>>
The user shall be able to determine the elapsed playback time of an audio track.
<<<
RELATIONS:
- TYPE: Parent
  VALUE: BR-005

[REQUIREMENT]
UID: UR-009
TITLE: Seek Playback Position
STATEMENT: >>>
The user shall be able to seek to a requested position within an audio track.
<<<
RELATIONS:
- TYPE: Parent
  VALUE: BR-005

[REQUIREMENT]
UID: UR-010
TITLE: Remaining Playback Time
STATEMENT: >>>
The user shall be able to determine the remaining playback time of an audio track.
<<<
RELATIONS:
- TYPE: Parent
  VALUE: BR-005

[REQUIREMENT]
UID: UR-011
TITLE: Playback Information
STATEMENT: >>>
The user shall be able to access and receive playback through the operating 
system's supported media-control interface, where available.
<<<
RELATIONS:
- TYPE: Parent
  VALUE: BR-005

[[/SECTION]]

[[SECTION]]
TITLE: Audio Playback Customization

[REQUIREMENT]
UID: UR-012
TITLE: Playback Speed
STATEMENT: The user shall be able to adjust the playback speed of an audio track.
RELATIONS:
- TYPE: Parent
  VALUE: BR-006

[REQUIREMENT]
UID: UR-013
TITLE: Playback Pitch
STATEMENT: >>>
The user shall be able to adjust the playback pitch of an audio track independently 
of playback speed.
<<<
RELATIONS:
- TYPE: Parent
  VALUE: BR-006

[REQUIREMENT]
UID: UR-014
TITLE: Playback Volume
STATEMENT: The user shall be able to adjust the playback volume of an audio track.
RELATIONS:
- TYPE: Parent
  VALUE: BR-006

[REQUIREMENT]
UID: UR-015
TITLE: Audio Processing Configuration
STATEMENT: >>>
The user shall be able to configure the available audio processing options.
<<<
RELATIONS:
- TYPE: Parent
  VALUE: BR-006

[REQUIREMENT]
UID: UR-016
TITLE: Active Playback Customisations
STATEMENT: >>>
The user shall be able to determine which playback customizations are 
currently active.
<<<
RELATIONS:
- TYPE: Parent
  VALUE: BR-006

[[/SECTION]]

[[/SECTION]]

[[SECTION]]
TITLE: File Organisation

[[SECTION]]
TITLE: Audio Library

[REQUIREMENT]
UID: UR-017
TITLE: Adding local files
STATEMENT: >>>
The user shall be able to add supported audio files stored on their devices 
to their library.
<<<
RELATIONS:
- TYPE: Parent
  VALUE: BR-002
- TYPE: Parent
  VALUE: BR-007

[REQUIREMENT]
UID: UR-018
TITLE: Adding Remote files
STATEMENT: >>>
The user shall be able to add supported audio files stored with a connected 
cloud provider to their library.
<<<
RELATIONS:
- TYPE: Parent
  VALUE: BR-003
- TYPE: Parent
  VALUE: BR-007

[REQUIREMENT]
UID: UR-019
TITLE: Remove files
STATEMENT: >>>
The user shall be able to remove audio files from their library.
<<<
RELATIONS:
- TYPE: Parent
  VALUE: BR-007

[REQUIREMENT]
UID: UR-020
TITLE: Accessing Files
STATEMENT: >>>
The user shall be able to browse their library and select audio files from it.
<<<
RELATIONS:
- TYPE: Parent
  VALUE: BR-007

[REQUIREMENT]
UID: UR-021
TITLE: Undo and Redo library Changes
STATEMENT: >>>
The user shall be able to undo and redo changes to a library.
<<<
RELATIONS:
- TYPE: Parent
  VALUE: BR-019

[REQUIREMENT]
UID: UR-104
TITLE: Library Persistence
STATEMENT: >>>
The user shall be able to access their library across application sessions.
<<<
RELATIONS:
- TYPE: Parent
  VALUE: BR-007

[[/SECTION]]

[[SECTION]]
TITLE: Searching, Sorting, Filtering and Tagging

[REQUIREMENT]
UID: UR-022
TITLE: Tag Management
STATEMENT: >>>
The user shall be able to create tags and assign them to audio files
in their library.
<<<
RELATIONS:
- TYPE: Parent
  VALUE: BR-008

[REQUIREMENT]
UID: UR-023
TITLE: Library Searching
STATEMENT: >>>
The user shall be able to search their library using tags or supported track
attributes.
<<<
RELATIONS:
- TYPE: Parent
  VALUE: BR-008

[REQUIREMENT]
UID: UR-024
TITLE: Library Sorting
STATEMENT: >>>
The user shall be able to sort library tracks using tags or supported track 
attributes.
<<<
RELATIONS:
- TYPE: Parent
  VALUE: BR-008

[REQUIREMENT]
UID: UR-025
TITLE: Library Filtering
STATEMENT: >>>
The user shall be able to filter library tracks using tags or supported track 
attributes.
<<<
RELATIONS:
- TYPE: Parent
  VALUE: BR-008

[REQUIREMENT]
UID: UR-026
TITLE: Empty Search and Filter Results
STATEMENT: >>>
The user shall be able to identify when a search or filter produces no matching 
tracks.
<<<
RELATIONS:
- TYPE: Parent
  VALUE: BR-008

[[/SECTION]]

[[SECTION]]
TITLE: Track Metadata

[REQUIREMENT]
UID: UR-027
TITLE: Viewing Track Metadata
STATEMENT: >>>
The user shall be able to view the available metadata for an audio track.
<<<
RELATIONS:
- TYPE: Parent
  VALUE: BR-009

[REQUIREMENT]
UID: UR-028
TITLE: Modifying Track Metadata
STATEMENT: >>>
The user shall be able to modify editable metadata fields for an audio track.
<<<
RELATIONS:
- TYPE: Parent
  VALUE: BR-009

[REQUIREMENT]
UID: UR-105
TITLE: Undo and Redo Track Metadata Changes
STATEMENT: >>>
The user shall be able to undo and redo changes to a library.
<<<
RELATIONS:
- TYPE: Parent
  VALUE: BR-019

[REQUIREMENT]
UID: UR-029
TITLE: Saving Track Metadata
STATEMENT: >>>
The user shall be able to save metadata changes for an audio track.
<<<
RELATIONS:
- TYPE: Parent
  VALUE: BR-009

[REQUIREMENT]
UID: UR-030
TITLE: Identifying Non-Editable Metadata Fields
STATEMENT: >>>
The user shall be able to identify metadata fields that cannot be modified.
<<<
RELATIONS:
- TYPE: Parent
  VALUE: BR-009

[[/SECTION]]

[[/SECTION]]

[[SECTION]]
TITLE: Queues, Playlists and Collections

[[SECTION]]
TITLE: Playlists and Collections

[[SECTION]]
TITLE: Playlist and Collection Management

[REQUIREMENT]
UID: UR-031
TITLE: Playlist and Collection Creation
STATEMENT: >>>
The user shall be able to create playlists and collections of audio tracks.
<<<
RELATIONS:
- TYPE: Parent
  VALUE: BR-011

[REQUIREMENT]
UID: UR-032
TITLE: Adding to Playlists and Collections
STATEMENT: >>>
The user shall be able to add entries to playlists and collections.
<<<
RELATIONS:
- TYPE: Parent
  VALUE: BR-011

[REQUIREMENT]
UID: UR-033
TITLE: Removing from Playlists and Collections
STATEMENT: >>>
The user shall be able to remove tracks from playlists and collections without 
removing the tracks from their library.
<<<
RELATIONS:
- TYPE: Parent
  VALUE: BR-011

[REQUIREMENT]
UID: UR-034
TITLE: Playlist Organisation
STATEMENT: >>>
The user shall be able to change the order of tracks inside of playlists 
and collections.
<<<
RELATIONS:
- TYPE: Parent
  VALUE: BR-011

[REQUIREMENT]
UID: UR-035
TITLE: Playlist and collection Metadata
STATEMENT: >>>
The user shall be able to view and modify playlist and collection metadata.
<<<
RELATIONS:
- TYPE: Parent
  VALUE: BR-011

[REQUIREMENT]
UID: UR-102
TITLE: Undo and Redo playlist and collection Changes
STATEMENT: >>>
The user shall be able to undo and redo changes to a playlist or collection.
<<<
RELATIONS:
- TYPE: Parent
  VALUE: BR-019

[REQUIREMENT]
UID: UR-103
TITLE: Undo and Redo metadata Changes
STATEMENT: >>>
The user shall be able to undo and redo changes to the metadata of a playlist or
collection.
<<<
RELATIONS:
- TYPE: Parent
  VALUE: BR-019

[REQUIREMENT]
UID: UR-036
TITLE: Playlist and Collection Persistence
STATEMENT: >>>
The user shall be able to access their saved playlists and collections across 
application sessions.
<<<
RELATIONS:
- TYPE: Parent
  VALUE: BR-011

[[/SECTION]]

[[SECTION]]
TITLE: Searching, Sorting and Filtering

[REQUIREMENT]
UID: UR-037
TITLE: Tag Management
STATEMENT: >>>
The user shall be able to create tags and assign them to audio files
in their playlists or collections.
<<<
RELATIONS:
- TYPE: Parent
  VALUE: BR-008

[REQUIREMENT]
UID: UR-038
TITLE: Playlist and Collection Searching
STATEMENT: >>>
The user shall be able to search their playlists and collections using tags or 
supported track attributes.
<<<
RELATIONS:
- TYPE: Parent
  VALUE: BR-008

[REQUIREMENT]
UID: UR-039
TITLE: Library Sorting
STATEMENT: >>>
The user shall be able to sort tracks inside of playlists and collections using 
tags or supported track attributes.
<<<
RELATIONS:
- TYPE: Parent
  VALUE: BR-008

[REQUIREMENT]
UID: UR-040
TITLE: Library Filtering
STATEMENT: >>>
The user shall be able to filter tracks inside of playlists and collections using 
tags or supported track attributes.
<<<
RELATIONS:
- TYPE: Parent
  VALUE: BR-008

[REQUIREMENT]
UID: UR-041
TITLE: Empty Search and Filter Results
STATEMENT: >>>
The user shall be able to identify when a search or filter produces no matching 
tracks.
<<<
RELATIONS:
- TYPE: Parent
  VALUE: BR-008

[[/SECTION]]

[[/SECTION]]

[[SECTION]]
TITLE: Playback Queue

[[SECTION]]
TITLE: Queue Management

[REQUIREMENT]
UID: UR-042
TITLE: View Playback Queues
STATEMENT: >>>
The user shall be able to view playback decks and their associated queues.
<<<
RELATIONS:
- TYPE: Parent
  VALUE: BR-012

[REQUIREMENT]
UID: UR-043
TITLE: Identify Currently Playing Queues
STATEMENT: >>>
The user shall be able to identify playback decks currently in use.
<<<
RELATIONS:
- TYPE: Parent
  VALUE: BR-012

[REQUIREMENT]
UID: UR-044
TITLE: Select Playback Queues
STATEMENT: >>>
The user shall be able to select playback queues for playback control.
<<<
RELATIONS:
- TYPE: Parent
  VALUE: BR-012

[REQUIREMENT]
UID: UR-045
TITLE: Create and Delete Playback Queues
STATEMENT: The user shall be able to create and delete playback queues.
RELATIONS:
- TYPE: Parent
  VALUE: BR-012

[REQUIREMENT]
UID: UR-046
TITLE: Add and Remove Tracks to Playback Queues
STATEMENT: The user shall be able to add and remove tracks to their playback queues.
RELATIONS:
- TYPE: Parent
  VALUE: BR-012

[REQUIREMENT]
UID: UR-047
TITLE: Rearrange Playback Queue
STATEMENT: The user shall be able to rearrange the contents of the playback queues.
RELATIONS:
- TYPE: Parent
  VALUE: BR-013

[REQUIREMENT]
UID: UR-048
TITLE: Undo and Redo Queue Changes
STATEMENT: >>>
The user shall be able to undo and redo changes to a queue.
<<<
RELATIONS:
- TYPE: Parent
  VALUE: BR-019

[REQUIREMENT]
UID: UR-049
TITLE: Independent Playback Decks
STATEMENT: >>>
The user shall be able to control each playback deck independently of other 
playback decks.
<<<
RELATIONS:
- TYPE: Parent
  VALUE: BR-012

[REQUIREMENT]
UID: UR-050
TITLE: Simultaneous Playback
STATEMENT: >>>
The user shall be able to play audio simultaneously on at least two playback decks.
<<<
RELATIONS:
- TYPE: Parent
  VALUE: BR-012

[REQUIREMENT]
UID: UR-051
TITLE: Playback Queue Switching Behaviour
STATEMENT: >>>
The user shall be able to configure the behaviour of a playback deck when 
switching its associated playback queue during playback.
<<<
RELATIONS:
- TYPE: Parent
  VALUE: BR-012

[[/SECTION]]

[[SECTION]]
TITLE: Searching, Sorting, Filtering and Tagging

[REQUIREMENT]
UID: UR-052
TITLE: Tag Management
STATEMENT: >>>
The user shall be able to create tags and assign them to audio files
in their playback queues.
<<<
RELATIONS:
- TYPE: Parent
  VALUE: BR-008

[REQUIREMENT]
UID: UR-053
TITLE: Queue Searching
STATEMENT: >>>
The user shall be able to search their queues using tags or supported track 
attributes.
<<<
RELATIONS:
- TYPE: Parent
  VALUE: BR-008

[REQUIREMENT]
UID: UR-054
TITLE: Queue Sorting
STATEMENT: >>>
The user shall be able to sort tracks inside of queues using 
tags or supported track attributes.
<<<
RELATIONS:
- TYPE: Parent
  VALUE: BR-008

[REQUIREMENT]
UID: UR-055
TITLE: Queue Filtering
STATEMENT: >>>
The user shall be able to filter tracks inside of queues using 
tags or supported track attributes.
<<<
RELATIONS:
- TYPE: Parent
  VALUE: BR-008

[REQUIREMENT]
UID: UR-056
TITLE: Empty Search and Filter Results
STATEMENT: >>>
The user shall be able to identify when a search or filter produces no matching 
tracks.
<<<
RELATIONS:
- TYPE: Parent
  VALUE: BR-008

[[/SECTION]]

[[/SECTION]]

[[/SECTION]]

[[SECTION]]
TITLE: Personalisation

[[SECTION]]
TITLE: User Preferences

[REQUIREMENT]
UID: UR-057
TITLE: Configure Application Preferences
STATEMENT: The user shall be able to configure application preferences.
RELATIONS:
- TYPE: Parent
  VALUE: BR-014

[REQUIREMENT]
UID: UR-058
TITLE: Configure Playback Preferences
STATEMENT: The user shall be able to configure playback preferences.
RELATIONS:
- TYPE: Parent
  VALUE: BR-014

[REQUIREMENT]
UID: UR-107
TITLE: Configure Interface Preferences
STATEMENT: The user shall be able to configure Interface preferences.
RELATIONS:
- TYPE: Parent
  VALUE: BR-014

[REQUIREMENT]
UID: UR-059
TITLE: View Preference Settings
STATEMENT: >>>
The user shall be able to view their current preferences.
<<<
RELATIONS:
- TYPE: Parent
  VALUE: BR-014

[REQUIREMENT]
UID: UR-060
TITLE: Retain Preference Settings
STATEMENT: >>>
The user shall be able to retain configured preferences between playback sessions.
<<<
RELATIONS:
- TYPE: Parent
  VALUE: BR-014

[REQUIREMENT]
UID: UR-108
TITLE: Reset Preferences
STATEMENT: >>>
The user shall be able to restore default preferences.
<<<
RELATIONS:
- TYPE: Parent
  VALUE: BR-014

[[/SECTION]]

[[SECTION]]
TITLE: Internationalization

[REQUIREMENT]
UID: UR-061
TITLE: View Language
STATEMENT: >>>
The user shall be able to view the languages available for use by the application.
<<<
RELATIONS:
- TYPE: Parent
  VALUE: BR-015

[REQUIREMENT]
UID: UR-062
TITLE: Select Application Language
STATEMENT: >>>
The user shall be able to select an available application language.
<<<
RELATIONS:
- TYPE: Parent
  VALUE: BR-015

[REQUIREMENT]
UID: UR-063
TITLE: Use Selected Language
STATEMENT: >>>
The user shall be able to use the application in the selected language.
<<<
RELATIONS:
- TYPE: Parent
  VALUE: BR-015

[REQUIREMENT]
UID: UR-064
TITLE: Update Installed Additional Languages
STATEMENT: >>>
The user shall be able to update the installed languages using external sources.
<<<
RELATIONS:
- TYPE: Parent
  VALUE: BR-015

[REQUIREMENT]
UID: UR-065
TITLE: Language Settings Persistence
STATEMENT: >>>
The user shall be able to retain the selected Language between playback sessions.
<<<
RELATIONS:
- TYPE: Parent
  VALUE: BR-014

[[/SECTION]]

[[/SECTION]]

[[SECTION]]
TITLE: Analytics

[[SECTION]]
TITLE: Library Activity

[REQUIREMENT]
UID: UR-066
TITLE: Viewing Library Activity
STATEMENT: >>>
The user shall be able to view information about their library activity.
<<<
RELATIONS:
- TYPE: Parent
  VALUE: BR-010

[REQUIREMENT]
UID: UR-067
TITLE: Deleting Library Activity
STATEMENT: >>>
The user shall be able to delete recorded library activity information.
<<<
RELATIONS:
- TYPE: Parent
  VALUE: BR-010

[REQUIREMENT]
UID: UR-068
TITLE: Reviewing Historical Library Activity
STATEMENT: >>>
The user shall be able to review their library activity over user-defined 
time periods.
<<<
RELATIONS:
- TYPE: Parent
  VALUE: BR-016

[REQUIREMENT]
UID: UR-069
TITLE: Analyse Library Activity
STATEMENT: >>>
The user shall be able to analyse their library activity information over 
user-defined time periods.
<<<
RELATIONS:
- TYPE: Parent
  VALUE: BR-016

[[/SECTION]]

[[SECTION]]
TITLE: Listening Analytics

[REQUIREMENT]
UID: UR-070
TITLE: Viewing Listening Behaviour
STATEMENT: >>>
The user shall be able to view information about their listening behaviour.
<<<
RELATIONS:
- TYPE: Parent
  VALUE: BR-016

[REQUIREMENT]
UID: UR-071
TITLE: Deleting Listening Behaviour
STATEMENT: The user shall be able to delete recorded listening history.
RELATIONS:
- TYPE: Parent
  VALUE: BR-016

[REQUIREMENT]
UID: UR-072
TITLE: Reviewing Listening Behaviour
STATEMENT: >>>
The user shall be able to review listening information over user-defined 
time periods.
<<<
RELATIONS:
- TYPE: Parent
  VALUE: BR-016

[REQUIREMENT]
UID: UR-073
TITLE: Analysing Listening Behaviour
STATEMENT: >>>
The user shall be able to analyse their listening behaviour over user-defined 
time periods.
<<<
RELATIONS:
- TYPE: Parent
  VALUE: BR-016

[[/SECTION]]

[[/SECTION]]

[[SECTION]]
TITLE: Interoperability

[[SECTION]]
TITLE: Sharing

[REQUIREMENT]
UID: UR-074
TITLE: Sharing Audio-Related Information
STATEMENT: >>>
The user shall be able to share supported audio-related information with 
compatible external applications or services.
<<<
RELATIONS:
- TYPE: Parent
  VALUE: BR-017

[REQUIREMENT]
UID: UR-075
TITLE: Synchronize Playback Across Devices
STATEMENT: >>>
The user shall be able to synchronize playback between supported devices.
<<<
RELATIONS:
- TYPE: Parent
  VALUE: BR-017

[REQUIREMENT]
UID: UR-076
TITLE: Identifying External Integrations
STATEMENT: >>>
The user shall be able to identify which external applications, services, or 
devices are available for supported interactions.
<<<
RELATIONS:
- TYPE: Parent
  VALUE: BR-017

[[/SECTION]]

[[/SECTION]]

[[SECTION]]
TITLE: User Interaction

[[SECTION]]
TITLE: User Interface Types

[REQUIREMENT]
UID: UR-077
TITLE: TUI Interface
STATEMENT: >>>
The user shall be able to access Yaap through a text-based user interface.
<<<
RELATIONS:
- TYPE: Parent
  VALUE: BR-018

[REQUIREMENT]
UID: UR-078
TITLE: GUI Interface
STATEMENT: >>>
The user shall be able to access Yaap through a graphical user interface.
<<<
RELATIONS:
- TYPE: Parent
  VALUE: BR-018

[REQUIREMENT]
UID: UR-079
TITLE: Identify Controls
STATEMENT: >>>
The user shall be able to identify the available controls and how to use them.
<<<
RELATIONS:
- TYPE: Parent
  VALUE: BR-018

[REQUIREMENT]
UID: UR-080
TITLE: Customise Controls
STATEMENT: >>>
The user shall be able to customise the controls used to interact with Yaap.
<<<
RELATIONS:
- TYPE: Parent
  VALUE: BR-018

[REQUIREMENT]
UID: UR-081
TITLE: Perform Actions through Interaction Modes
STATEMENT: >>>
The user shall be able to perform supported operations through the available 
interaction modes.
<<<
RELATIONS:
- TYPE: Parent
  VALUE: BR-018

[[/SECTION]]

[[/SECTION]]

[[SECTION]]
TITLE: Data Management

[[SECTION]]
TITLE: Operation Recovery

[REQUIREMENT]
UID: UR-082
TITLE: Undo Actions
STATEMENT: The user shall be able to undo supported actions.
RELATIONS:
- TYPE: Parent
  VALUE: BR-019

[REQUIREMENT]
UID: UR-083
TITLE: Redo Actions
STATEMENT: >>>
The user shall be able to redo supported actions.
<<<
RELATIONS:
- TYPE: Parent
  VALUE: BR-019

[REQUIREMENT]
UID: UR-084
TITLE: View Action Tree
STATEMENT: >>>
The user shall be able to view the history of actions performed during the 
current session.
<<<
RELATIONS:
- TYPE: Parent
  VALUE: BR-019

[REQUIREMENT]
UID: UR-085
TITLE: Identify Undoable and Redoable Actions
STATEMENT: >>>
The user shall be able to determine which actions can currently be undone 
or redone.
<<<
RELATIONS:
- TYPE: Parent
  VALUE: BR-019

[[/SECTION]]

[[SECTION]]
TITLE: Importing and Exporting User Data

[REQUIREMENT]
UID: UR-086
TITLE: Import User-Created Information
STATEMENT: >>>
The user shall be able to import user-created information.
<<<
RELATIONS:
- TYPE: Parent
  VALUE: BR-020

[REQUIREMENT]
UID: UR-087
TITLE: Export User-Created Information
STATEMENT: >>>
The user shall be able to export user-created information.
<<<
RELATIONS:
- TYPE: Parent
  VALUE: BR-020

[REQUIREMENT]
UID: UR-106
TITLE: Selecting Shared Information Categories
STATEMENT: >>>
The user shall be able to select which supported categories of user-created 
information to import or export.
<<<
RELATIONS:
- TYPE: Parent
  VALUE: BR-020

[[/SECTION]]

[[/SECTION]]

[[SECTION]]
TITLE: Lyrics

[[SECTION]]
TITLE: Display Lyrics

[REQUIREMENT]
UID: UR-088
TITLE: View Lyrics
STATEMENT: >>>
The user shall be able to view lyrics associated with an audio track.
<<<
RELATIONS:
- TYPE: Parent
  VALUE: BR-021

[REQUIREMENT]
UID: UR-089
TITLE: Modify Lyrics
STATEMENT: >>>
The user shall be able to modify lyrics associated with an audio track.
<<<
RELATIONS:
- TYPE: Parent
  VALUE: BR-021

[REQUIREMENT]
UID: UR-090
TITLE: Toggle Lyrics
STATEMENT: >>>
The user shall be able to enable and disable lyric visualisation for an audio track.
<<<
RELATIONS:
- TYPE: Parent
  VALUE: BR-021

[REQUIREMENT]
UID: UR-109
TITLE: Lyrics Selection
STATEMENT: >>>
The user shall be able to select which available lyrics associated with an audio 
track are displayed.
<<<
RELATIONS:
- TYPE: Parent
  VALUE: BR-021

[REQUIREMENT]
UID: UR-110
TITLE: Display Synchronized Lyrics on Other Devices
STATEMENT: >>>
The user shall be able to display lyrics synchronised with audio playback 
on other supported devices.
<<<
RELATIONS:
- TYPE: Parent
  VALUE: BR-017
- TYPE: Parent
  VALUE: BR-021

[[/SECTION]]

[[SECTION]]
TITLE: Translate Lyrics

[REQUIREMENT]
UID: UR-091
TITLE: Translate Lyrics
STATEMENT: The user shall be able to translate lyrics.
RELATIONS:
- TYPE: Parent
  VALUE: BR-022

[REQUIREMENT]
UID: UR-092
TITLE: Change Translations
STATEMENT: >>>
The user shall be able to switch between different lyric translations for a given 
audio track.
<<<
RELATIONS:
- TYPE: Parent
  VALUE: BR-022

[[/SECTION]]

[[SECTION]]
TITLE: Align Lyrics

[REQUIREMENT]
UID: UR-093
TITLE: Align Lyrics
STATEMENT: The user shall be able to align lyrics to different levels
RELATIONS:
- TYPE: Parent
  VALUE: BR-022

[REQUIREMENT]
UID: UR-094
TITLE: Align Lyrics
STATEMENT: >>>
The user shall be able to switch between different lyric alignments for a given 
audio track.
<<<
RELATIONS:
- TYPE: Parent
  VALUE: BR-022

[[/SECTION]]

[[SECTION]]
TITLE: Download Lyrics

[REQUIREMENT]
UID: UR-095
TITLE: Download Track Lyrics
STATEMENT: >>>
The user shall be able to download lyrics associated with tracks in their library.
<<<
RELATIONS:
- TYPE: Parent
  VALUE: BR-023

[REQUIREMENT]
UID: UR-096
TITLE: Select Lyrics Downloaded Source
STATEMENT: >>>
The user shall be able to select the source from which lyrics are downloaded, where multiple sources are available.
<<<
RELATIONS:
- TYPE: Parent
  VALUE: BR-023

[REQUIREMENT]
UID: UR-097
TITLE: Select Lyrics Downloaded Alignment
STATEMENT: >>>
The user shall be able to select the alignment of the lyrics to be downloaded, 
where multiple alignments are available.
<<<
RELATIONS:
- TYPE: Parent
  VALUE: BR-023

[[/SECTION]]

[[/SECTION]]

[[SECTION]]
TITLE: Audio Visualisation

[[SECTION]]
TITLE: Audio Visualisation

[REQUIREMENT]
UID: UR-098
TITLE: View Audio Visualisations
STATEMENT: >>>
The user shall be able to view visual representations of audio during playback.
<<<
RELATIONS:
- TYPE: Parent
  VALUE: BR-024

[REQUIREMENT]
UID: UR-099
TITLE: Customise Audio Visualisation
STATEMENT: >>>
The user shall be able to customise the appearance and behaviour of audio 
visualisations.
<<<
RELATIONS:
- TYPE: Parent
  VALUE: BR-024

[REQUIREMENT]
UID: UR-100
TITLE: Toggle Audio Visualisation
STATEMENT: >>>
The user shall be able to enable and disable audio visualisation during playback.
<<<
RELATIONS:
- TYPE: Parent
  VALUE: BR-024

[REQUIREMENT]
UID: UR-101
TITLE: Retain Audio Visualisation Settings
STATEMENT: >>>
The user shall be able to retain configured audio visualisation settings between 
application settings.
<<<
RELATIONS:
- TYPE: Parent
  VALUE: BR-024

[REQUIREMENT]
UID: UR-120
TITLE: Display Synchronized Audio Visualisations on Other Devices
STATEMENT: >>>
The user shall be able to display audio visualisations synchronized with audio
playback on other supported devices.
<<<
RELATIONS:
- TYPE: Parent
  VALUE: BR-017
- TYPE: Parent
  VALUE: BR-024

[[/SECTION]]

[[/SECTION]]
