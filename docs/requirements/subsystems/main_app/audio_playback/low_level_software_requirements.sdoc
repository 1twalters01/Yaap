[DOCUMENT]
TITLE: Audio Playback Low Level Software Requirements
UID: YAAP-APLLSR
DATE: @GIT_COMMIT_DATETIME
PREFIX: APLLSR-

[[SECTION]]
TITLE: Introduction

[TEXT]
STATEMENT: >>>
This document defines the low level software requirements for Yet Another 
Audio Player (Yaap), a time accurate desktop audio player.
<<<

[[/SECTION]]

[[SECTION]]
TITLE: File Handling

[[SECTION]]
TITLE: File Type Identification

[REQUIREMENT]
UID: APLLSR-001
TITLE: Supported Format Detection
STATEMENT: >>>
The software shall determine whether an input audio stream's identified format 
and encoding are supported.
<<<
RELATIONS:
- TYPE: Parent
  VALUE: APHLSR-001

[REQUIREMENT]
UID: APLLSR-002
TITLE: Unsupported Format Error Generation
STATEMENT: >>>
The software shall generate an unsupported-format error when an input audio
stream's format or encoding is unsupported.
<<<
RELATIONS:
- TYPE: Parent
  VALUE: APHLSR-001

[REQUIREMENT]
UID: APLLSR-003
TITLE: Unknown Format Error Generation
STATEMENT: >>>
The software shall generate an unknown-format error when an input audio
stream's format is unknown.
<<<
RELATIONS:
- TYPE: Parent
  VALUE: APHLSR-001

[REQUIREMENT]
UID: APLLSR-004
TITLE: Unknown Encoding Error Generation
STATEMENT: >>>
The software shall generate an unknown-encoding error when an input audio
stream's encoding is unknown.
<<<
RELATIONS:
- TYPE: Parent
  VALUE: APHLSR-001

[REQUIREMENT]
UID: APLLSR-005
TITLE: Invalid Format Error Generation
STATEMENT: >>>
The software shall generate an invalid-format error when an input audio
stream's format or encoding is invalid.
<<<
RELATIONS:
- TYPE: Parent
  VALUE: APHLSR-001

[REQUIREMENT]
UID: APLLSR-006
TITLE: FLAC Encoding Identification
STATEMENT: >>>
The software shall identify whether an input audio stream is encoded in the 
FLAC format.
<<<
RELATIONS:
- TYPE: Parent
  VALUE: APHLSR-004

[REQUIREMENT]
UID: APLLSR-007
TITLE: FLAC Identification Independent of Extension
STATEMENT: >>>
The software shall identify FLAC audio streams independently from the stream's 
filename extension.
<<<
RELATIONS:
- TYPE: Parent
  VALUE: APHLSR-004

[[/SECTION]]

[[/SECTION]]
