[DOCUMENT]
TITLE: Audio Playback Subsystem Requirements
UID: YAAP-APSSR
DATE: @GIT_COMMIT_DATETIME
PREFIX: APSSR-

[[SECTION]]
TITLE: Introduction

[TEXT]
STATEMENT: >>>
This document defines the subsystem requirements for Yet Another Audio Player
(Yaap), a time accurate desktop audio player.
<<<

[[/SECTION]]

[[SECTION]]
TITLE: File Handling

[[SECTION]]
TITLE: FLAC File Handling

[REQUIREMENT]
UID: APSSR-001
TITLE: FLAC File Input Access
STATEMENT: >>>
The subsystem shall support FLAC files as audio input sources.
<<<
RELATIONS:
- TYPE: Parent
  VALUE: SR-001

[REQUIREMENT]
UID: APSSR-002
TITLE: FLAC Format Identification
STATEMENT: >>>
The subsystem shall identify whether an input file contains an audio stream 
encoded in the FLAC format.
<<<
RELATIONS:
- TYPE: Parent
  VALUE: SR-001
- TYPE: Parent
  VALUE: SR-009

[REQUIREMENT]
UID: APSSR-003
TITLE: FLAC File Decoding
STATEMENT: >>>
The subsystem shall decode supported audio streams encoded in the FLAC format
into PCM audio samples.
<<<
RELATIONS:
- TYPE: Parent
  VALUE: SR-001

[REQUIREMENT]
UID: APSSR-004
TITLE: FLAC File Channel Extraction
STATEMENT: >>>
The subsystem shall obtain the number of audio channels from FLAC audio
streams.
<<<
RELATIONS:
- TYPE: Parent
  VALUE: SR-001

[REQUIREMENT]
UID: APSSR-005
TITLE: FLAC File Sample Rate Extraction
STATEMENT: >>>
The subsystem shall obtain the sample rate of FLAC audio streams.
<<<
RELATIONS:
- TYPE: Parent
  VALUE: SR-001

[REQUIREMENT]
UID: APSSR-006
TITLE: FLAC File Bits Per Sample Extraction
STATEMENT: >>>
The subsystem shall obtain the number of bits per sample from FLAC audio 
streams.
<<<
RELATIONS:
- TYPE: Parent
  VALUE: SR-001

[[/SECTION]]

[[SECTION]]
TITLE: MP3 File Handling

[REQUIREMENT]
UID: APSSR-007
TITLE: MP3 File Input Access
STATEMENT: >>>
The subsystem shall support MP3 files as audio input sources.
<<<
RELATIONS:
- TYPE: Parent
  VALUE: SR-002

[REQUIREMENT]
UID: APSSR-008
TITLE: MP3 Format Identification
STATEMENT: >>>
The subsystem shall identify whether an input file contains an audio stream 
encoded in the MP3 format.
<<<
RELATIONS:
- TYPE: Parent
  VALUE: SR-002
- TYPE: Parent
  VALUE: SR-009

[REQUIREMENT]
UID: APSSR-009
TITLE: MP3 File Decoding
STATEMENT: >>>
The subsystem shall decode supported audio streams contained within MP3 files 
into PCM audio samples.
<<<
RELATIONS:
- TYPE: Parent
  VALUE: SR-002

[REQUIREMENT]
UID: APSSR-010
TITLE: MP3 File Channel Extraction
STATEMENT: >>>
The subsystem shall obtain the number of audio channels from MP3 audio
streams.
<<<
RELATIONS:
- TYPE: Parent
  VALUE: SR-002

[REQUIREMENT]
UID: APSSR-011
TITLE: MP3 File Sample Rate Extraction
STATEMENT: >>>
The subsystem shall obtain the sample rate of MP3 audio streams.
<<<
RELATIONS:
- TYPE: Parent
  VALUE: SR-002

[REQUIREMENT]
UID: APSSR-012
TITLE: MP3 File Bitrate Extraction
STATEMENT: >>>
The subsystem shall obtain the bitrate of MP3 audio streams.
<<<
RELATIONS:
- TYPE: Parent
  VALUE: SR-002

[[/SECTION]]

[[SECTION]]
TITLE: WAV File Handling

[REQUIREMENT]
UID: APSSR-013
TITLE: WAV File Input Access
STATEMENT: >>>
The subsystem shall support WAV files as audio input sources.
<<<
RELATIONS:
- TYPE: Parent
  VALUE: SR-003

[REQUIREMENT]
UID: APSSR-014
TITLE: Audio Container Identification
STATEMENT: >>>
The subsystem shall identify WAV containers independently of the
codecs they contain.
<<<
RELATIONS:
- TYPE: Parent
  VALUE: SR-009

[REQUIREMENT]
UID: APSSR-015
TITLE: WAV Format Identification
STATEMENT: >>>
The subsystem shall identify whether an input file uses the WAV container 
format.
<<<
RELATIONS:
- TYPE: Parent
  VALUE: SR-009

[REQUIREMENT]
UID: APSSR-016
TITLE: WAV File Decoding
STATEMENT: >>>
The subsystem shall decode supported audio streams contained within WAV files 
into PCM audio samples.
<<<
RELATIONS:
- TYPE: Parent
  VALUE: SR-003

[REQUIREMENT]
UID: APSSR-017
TITLE: WAV File Channel Extraction
STATEMENT: >>>
The subsystem shall obtain the number of audio channels from audio streams 
contained within WAV files.
<<<
RELATIONS:
- TYPE: Parent
  VALUE: SR-003

[REQUIREMENT]
UID: APSSR-018
TITLE: WAV File Sample Rate Extraction
STATEMENT: >>>
The subsystem shall obtain the sample rate of audio streams contained within 
WAV files.
<<<
RELATIONS:
- TYPE: Parent
  VALUE: SR-003

[REQUIREMENT]
UID: APSSR-019
TITLE: WAV File Bits Per Sample Extraction
STATEMENT: >>>
The subsystem shall obtain the number of bits per sample from audio streams 
contained within WAV files.
<<<
RELATIONS:
- TYPE: Parent
  VALUE: SR-003

[[/SECTION]]

[[SECTION]]
TITLE: AAC Audio Handling

[REQUIREMENT]
UID: APSSR-020
TITLE: AAC Input Access
STATEMENT: >>>
The subsystem shall support AAC-encoded audio files as audio input sources.
<<<
RELATIONS:
- TYPE: Parent
  VALUE: SR-004

[REQUIREMENT]
UID: APSSR-021
TITLE: Audio Container Identification
STATEMENT: >>>
The subsystem shall identify the container format of input sources containing 
AAC-encoded audio.
<<<
RELATIONS:
- TYPE: Parent
  VALUE: SR-009

[REQUIREMENT]
UID: APSSR-022
TITLE: AAC Stream Identification
STATEMENT: >>>
The subsystem shall identify whether an input source contains AAC-encoded 
audio.
<<<
RELATIONS:
- TYPE: Parent
  VALUE: SR-004
- TYPE: Parent
  VALUE: SR-009

[REQUIREMENT]
UID: APSSR-023
TITLE: AAC Audio Decoding
STATEMENT: >>>
The subsystem shall decode supported AAC audio streams into PCM audio samples.
<<<
RELATIONS:
- TYPE: Parent
  VALUE: SR-004

[REQUIREMENT]
UID: APSSR-024
TITLE: AAC Audio Channel Extraction
STATEMENT: >>>
The subsystem shall obtain the number of audio channels from AAC audio streams.
<<<
RELATIONS:
- TYPE: Parent
  VALUE: SR-004

[REQUIREMENT]
UID: APSSR-025
TITLE: AAC Sample Rate Extraction
STATEMENT: >>>
The subsystem shall obtain the sample rate of AAC audio streams.
<<<
RELATIONS:
- TYPE: Parent
  VALUE: SR-004

[REQUIREMENT]
UID: APSSR-026
TITLE: AAC Bitrate Extraction
STATEMENT: >>>
The subsystem shall obtain the bitrate of audio streams 
contained within AAC files.
<<<
RELATIONS:
- TYPE: Parent
  VALUE: SR-004

[[/SECTION]]

[[SECTION]]
TITLE: ALAC File Handling

[REQUIREMENT]
UID: APSSR-027
TITLE: ALAC Audio Input Access
STATEMENT: >>>
The subsystem shall support ALAC-encoded audio files as audio input sources.
<<<
RELATIONS:
- TYPE: Parent
  VALUE: SR-005

[REQUIREMENT]
UID: APSSR-028
TITLE: ALAC Format Identification
STATEMENT: >>>
The subsystem shall identify whether an input file contains an audio stream 
encoded in the ALAC format.
<<<
RELATIONS:
- TYPE: Parent
  VALUE: SR-005
- TYPE: Parent
  VALUE: SR-009

[REQUIREMENT]
UID: APSSR-029
TITLE: ALAC Audio Decoding
STATEMENT: >>>
The subsystem shall decode supported ALAC audio streams into PCM audio samples.
<<<
RELATIONS:
- TYPE: Parent
  VALUE: SR-005

[REQUIREMENT]
UID: APSSR-030
TITLE: ALAC Audio Channel Extraction
STATEMENT: >>>
The subsystem shall obtain the number of audio channels from ALAC audio
streams.
<<<
RELATIONS:
- TYPE: Parent
  VALUE: SR-005

[REQUIREMENT]
UID: APSSR-031
TITLE: ALAC Audio Sample Rate Extraction
STATEMENT: >>>
The subsystem shall obtain the sample rate of ALAC audio streams.
<<<
RELATIONS:
- TYPE: Parent
  VALUE: SR-005

[REQUIREMENT]
UID: APSSR-032
TITLE: ALAC Audio Bits Per Sample Extraction
STATEMENT: >>>
The subsystem shall obtain the number of bits per sample from ALAC audio 
streams.
<<<
RELATIONS:
- TYPE: Parent
  VALUE: SR-005

[[/SECTION]]

[[SECTION]]
TITLE: Vorbis File Handling

[REQUIREMENT]
UID: APSSR-033
TITLE: Vorbis Audio Input Access
STATEMENT: >>>
The subsystem shall support Vorbis-encoded audio files as audio input sources.
<<<
RELATIONS:
- TYPE: Parent
  VALUE: SR-006

[REQUIREMENT]
UID: APSSR-034
TITLE: Vorbis Format Identification
STATEMENT: >>>
The subsystem shall identify whether an input file contains an audio stream 
encoded in the Vorbis format.
<<<
RELATIONS:
- TYPE: Parent
  VALUE: SR-006
- TYPE: Parent
  VALUE: SR-009

[REQUIREMENT]
UID: APSSR-035
TITLE: Vorbis Audio Decoding
STATEMENT: >>>
The subsystem shall decode supported Vorbis audio streams into PCM audio
samples.
<<<
RELATIONS:
- TYPE: Parent
  VALUE: SR-006

[REQUIREMENT]
UID: APSSR-036
TITLE: Vorbis Audio Channel Extraction
STATEMENT: >>>
The subsystem shall obtain the number of audio channels from Vorbis audio
streams.
<<<
RELATIONS:
- TYPE: Parent
  VALUE: SR-006

[REQUIREMENT]
UID: APSSR-037
TITLE: Vorbis Audio Sample Rate Extraction
STATEMENT: >>>
The subsystem shall obtain the sample rate of Vorbis audio streams.
<<<
RELATIONS:
- TYPE: Parent
  VALUE: SR-006

[REQUIREMENT]
UID: APSSR-038
TITLE: Vorbis Audio Bitrate Extraction
STATEMENT: >>>
The subsystem shall obtain the bitrate of Vorbis audio streams.
<<<
RELATIONS:
- TYPE: Parent
  VALUE: SR-006

[[/SECTION]]

[[SECTION]]
TITLE: Opus File Handling

[REQUIREMENT]
UID: APSSR-039
TITLE: Opus Audio Input Access
STATEMENT: >>>
The subsystem shall support Opus-encoded audio files as audio input sources.
<<<
RELATIONS:
- TYPE: Parent
  VALUE: SR-007

[REQUIREMENT]
UID: APSSR-040
TITLE: Opus Format Identification
STATEMENT: >>>
The subsystem shall identify whether an input file contains an audio stream 
encoded in the Opus format.
<<<
RELATIONS:
- TYPE: Parent
  VALUE: SR-007
- TYPE: Parent
  VALUE: SR-009

[REQUIREMENT]
UID: APSSR-041
TITLE: Opus Audio Decoding
STATEMENT: >>>
The subsystem shall decode supported Opus audio streams into PCM audio samples.
<<<
RELATIONS:
- TYPE: Parent
  VALUE: SR-007

[REQUIREMENT]
UID: APSSR-042
TITLE: Opus Audio Channel Extraction
STATEMENT: >>>
The subsystem shall obtain the number of audio channels from Opus audio
streams.
<<<
RELATIONS:
- TYPE: Parent
  VALUE: SR-007

[REQUIREMENT]
UID: APSSR-043
TITLE: Opus Audio Sample Rate Extraction
STATEMENT: >>>
The subsystem shall obtain the sample rate of decoded Opus audio streams.
<<<
RELATIONS:
- TYPE: Parent
  VALUE: SR-007

[REQUIREMENT]
UID: APSSR-044
TITLE: Opus Audio Bitrate Extraction
STATEMENT: >>>
The subsystem shall obtain the bitrate of Opus audio streams.
<<<
RELATIONS:
- TYPE: Parent
  VALUE: SR-007

[[/SECTION]]

[[SECTION]]
TITLE: AIFF File Handling

[REQUIREMENT]
UID: APSSR-045
TITLE: AIFF File Input Access
STATEMENT: >>>
The subsystem shall support AIFF files as audio input sources.
<<<
RELATIONS:
- TYPE: Parent
  VALUE: SR-008

[REQUIREMENT]
UID: APSSR-046
TITLE: AIFF Format Identification
STATEMENT: >>>
The subsystem shall identify whether an input file is encoded in the AIFF 
format.
<<<
RELATIONS:
- TYPE: Parent
  VALUE: SR-008
- TYPE: Parent
  VALUE: SR-009

[REQUIREMENT]
UID: APSSR-047
TITLE: AIFF File Decoding
STATEMENT: >>>
The subsystem shall decode supported audio data contained within AIFF files 
into PCM audio samples.
<<<
RELATIONS:
- TYPE: Parent
  VALUE: SR-008

[REQUIREMENT]
UID: APSSR-048
TITLE: AIFF File Channel Extraction
STATEMENT: >>>
The subsystem shall obtain the number of audio channels from AIFF audio
streams.
<<<
RELATIONS:
- TYPE: Parent
  VALUE: SR-008

[REQUIREMENT]
UID: APSSR-049
TITLE: AIFF File Sample Rate Extraction
STATEMENT: >>>
The subsystem shall obtain the sample rate of AIFF audio streams.
<<<
RELATIONS:
- TYPE: Parent
  VALUE: SR-008

[REQUIREMENT]
UID: APSSR-050
TITLE: AIFF File Bits Per Sample Extraction
STATEMENT: >>>
The subsystem shall obtain the number of bits per sample from AIFF audio 
streams.
<<<
RELATIONS:
- TYPE: Parent
  VALUE: SR-008

[[/SECTION]]

[[SECTION]]
TITLE: Audio File Error Handling

[REQUIREMENT]
UID: APSSR-051
TITLE: Unsupported Format Reporting
STATEMENT: >>>
The subsystem shall report when an input audio stream uses an unsupported
format or encoding.
<<<
RELATIONS:
- TYPE: Parent
  VALUE: SR-010

[REQUIREMENT]
UID: APSSR-052
TITLE: Invalid Audio Data Reporting
STATEMENT: >>>
The subsystem shall report when an input audio stream contains invalid or
corrupted data that prevents decoding.
<<<
RELATIONS:
- TYPE: Parent
  VALUE: SR-011

[[/SECTION]]

[[/SECTION]]

[[SECTION]]
TITLE: Local Audio Files

[[SECTION]]
TITLE: Local Audio File Selection

[REQUIREMENT]
UID: APSSR-053
TITLE: Local Audio File Selection Request
STATEMENT: >>>
The subsystem shall allow the user to initiate the selection of a local audio
file for playback.
<<<
RELATIONS:
- TYPE: Parent
  VALUE: SR-012

[REQUIREMENT]
UID: APSSR-054
TITLE: Selected Local Audio File Provision
STATEMENT: >>>
The subsystem shall make selected local audio files available for playback.
<<<
RELATIONS:
- TYPE: Parent
  VALUE: SR-012

[[/SECTION]]

[[SECTION]]
TITLE: Local Audio File Access

[REQUIREMENT]
UID: APSSR-055
TITLE: Local Audio File Opening
STATEMENT: >>>
The subsystem shall open a selected local audio file for reading.
<<<
RELATIONS:
- TYPE: Parent
  VALUE: SR-013

[REQUIREMENT]
UID: APSSR-056
TITLE: Local Audio File Reading
STATEMENT: >>>
The subsystem shall read data from an opened local audio file.
<<<
RELATIONS:
- TYPE: Parent
  VALUE: SR-013

[[/SECTION]]

[[SECTION]]
TITLE: Local Audio File Playback Failure

[REQUIREMENT]
UID: APSSR-057
TITLE: Local Audio File Opening Failure Reporting
STATEMENT: >>>
The subsystem shall report failures when opening a selected local audio file
for reading.
<<<
RELATIONS:
- TYPE: Parent
  VALUE: SR-014

[REQUIREMENT]
UID: APSSR-058
TITLE: Local Audio File Reading Failure Reporting
STATEMENT: >>>
The subsystem shall report failures when reading an opened local audio file.
<<<
RELATIONS:
- TYPE: Parent
  VALUE: SR-014

[REQUIREMENT]
UID: APSSR-059
TITLE: Local Audio File Playback Failure Reporting
STATEMENT: >>>
The subsystem shall report failures when a selected local file cannot be
played.
<<<
RELATIONS:
- TYPE: Parent
  VALUE: SR-124

[[/SECTION]]

[[/SECTION]]

[[SECTION]]
TITLE: Remote Audio Files

[[SECTION]]
TITLE: Cloud Storage Provider support

[REQUIREMENT]
UID: APSSR-060
TITLE: Google Drive Support
STATEMENT: >>>
The subsystem shall support integration with Google Drive.
<<<
RELATIONS:
- TYPE: Parent
  VALUE: SR-015

[REQUIREMENT]
UID: APSSR-061
TITLE: iCloud Drive Support
STATEMENT: >>>
The subsystem shall support integration with iCloud Drive.
<<<
RELATIONS:
- TYPE: Parent
  VALUE: SR-015

[REQUIREMENT]
UID: APSSR-062
TITLE: Dropbox Support
STATEMENT: >>>
The subsystem shall support integration with Dropbox.
<<<
RELATIONS:
- TYPE: Parent
  VALUE: SR-015

[REQUIREMENT]
UID: APSSR-063
TITLE: Microsoft OneDrive Support
STATEMENT: >>>
The subsystem shall support integration with Microsoft OneDrive.
<<<
RELATIONS:
- TYPE: Parent
  VALUE: SR-015

[[/SECTION]]

[[SECTION]]
TITLE: Cloud Storage Provider Authentication

[REQUIREMENT]
UID: APSSR-064
TITLE: Cloud Storage Provider Authentication
STATEMENT: >>>
The subsystem shall support authenticating with each supported cloud storage
provider.
<<<
RELATIONS:
- TYPE: Parent
  VALUE: SR-016

[REQUIREMENT]
UID: APSSR-065
TITLE: Cloud Storage Provider Authentication Failure Reporting
STATEMENT: >>>
The subsystem shall report when authentication with a supported cloud storage 
provider fails.
<<<
RELATIONS:
- TYPE: Parent
  VALUE: SR-018

[REQUIREMENT]
UID: APSSR-066
TITLE: Cloud Storage Provider Authentication Expiration Reporting
STATEMENT: >>>
The subsystem shall report when authentication with a supported cloud storage 
provider expires.
<<<
RELATIONS:
- TYPE: Parent
  VALUE: SR-135

[[/SECTION]]

[[SECTION]]
TITLE: Cloud Storage Provider Connection Management

[REQUIREMENT]
UID: APSSR-067
TITLE: Cloud Storage Provider Connection Establishment
STATEMENT: >>>
The subsystem shall support establishing connections to supported cloud storage
providers.
<<<
RELATIONS:
- TYPE: Parent
  VALUE: SR-127

[REQUIREMENT]
UID: APSSR-068
TITLE: Cloud Storage Provider Disconnection 
STATEMENT: >>>
The subsystem shall support disconnecting from supported cloud storage providers.
<<<
RELATIONS:
- TYPE: Parent
  VALUE: SR-129

[REQUIREMENT]
UID: APSSR-069
TITLE: Cloud Storage Provider Connection Status Reporting
STATEMENT: >>>
The system shall report the connection status of each configured cloud storage
provider.
<<<
RELATIONS:
- TYPE: Parent
  VALUE: SR-017

[[/SECTION]]

[[SECTION]]
TITLE: Cloud Storage Provider Connection Failure Handling

[REQUIREMENT]
UID: APSSR-070
TITLE: Cloud Storage Provider Connection Failure Reporting
STATEMENT: >>>
The system shall detect and report when a connection to a cloud storage 
provider fails.
<<<
RELATIONS:
- TYPE: Parent
  VALUE: SR-136

[REQUIREMENT]
UID: APSSR-071
TITLE: Cloud Storage Provider Connection Interruption Reporting
STATEMENT: >>>
The system shall detect and report when an established connection
to a cloud storage provider is interrupted.
<<<
RELATIONS:
- TYPE: Parent
  VALUE: SR-130

[[/SECTION]]

[[SECTION]]
TITLE: Cloud Storage Provider Connection Recovery

[REQUIREMENT]
UID: APSSR-072
TITLE: Cloud Storage Provider Connection Re-establishment
STATEMENT: >>>
The system shall support re-establishing interrupted connections to 
supported cloud storage providers.
<<<
RELATIONS:
- TYPE: Parent
  VALUE: SR-137

[REQUIREMENT]
UID: APSSR-073
TITLE: Cloud Storage Provider Authentication Recovery
STATEMENT: >>>
The system shall support restoring authenticated access to cloud storage 
providers following authentication expiration.
<<<
RELATIONS:
- TYPE: Parent
  VALUE: SR-137

[[/SECTION]]

[[SECTION]]
TITLE: Remote Audio File Selection

[REQUIREMENT]
UID: APSSR-074
TITLE: Remote Audio File Selection Request
STATEMENT: >>>
The subsystem shall allow the user to initiate the selection of a remote audio
file for playback through a connected cloud provider.
<<<
RELATIONS:
- TYPE: Parent
  VALUE: SR-019

[REQUIREMENT]
UID: APSSR-075
TITLE: Selected Remote Audio File Provision
STATEMENT: >>>
The subsystem shall make the remote audio file selected by the user available
for playback.
<<<
RELATIONS:
- TYPE: Parent
  VALUE: SR-019

[[/SECTION]]

[[SECTION]]
TITLE: Remote File Access

[REQUIREMENT]
UID: APSSR-076
TITLE: Remote Audio File Opening
STATEMENT: >>>
The subsystem shall open a remote audio file selected from a connected cloud 
storage provider for reading.
<<<
RELATIONS:
- TYPE: Parent
  VALUE: SR-020

[REQUIREMENT]
UID: APSSR-077
TITLE: Remote Audio File Reading
STATEMENT: >>>
The subsystem shall read data from an opened remote audio file.
<<<
RELATIONS:
- TYPE: Parent
  VALUE: SR-020

[[/SECTION]]

[[SECTION]]
TITLE: Remote Audio File Playback Failure

[REQUIREMENT]
UID: APSSR-078
TITLE: Remote Audio File Retrieval Failure Reporting
STATEMENT: >>>
The subsystem shall report failures when a selected remote audio file cannot be
retrieved from a connected cloud provider.
<<<
RELATIONS:
- TYPE: Parent
  VALUE: SR-021

[REQUIREMENT]
UID: APSSR-079
TITLE: Remote Audio File Opening Failure Reporting
STATEMENT: >>>
The subsystem shall report failures when opening a selected remote audio file 
for reading.
<<<
RELATIONS:
- TYPE: Parent
  VALUE: SR-021

[REQUIREMENT]
UID: APSSR-080
TITLE: Remote Audio File Reading Failure Reporting
STATEMENT: >>>
The subsystem shall report failures when reading an opened remote audio file.
<<<
RELATIONS:
- TYPE: Parent
  VALUE: SR-021

[REQUIREMENT]
UID: APSSR-081
TITLE: Remote Audio File Playback Failure Reporting
STATEMENT: >>>
The subsystem shall report failures when a selected remote file cannot be 
played.
<<<
RELATIONS:
- TYPE: Parent
  VALUE: SR-022

[REQUIREMENT]
UID: APSSR-082
TITLE: Remote Audio File Playback Interruption Reporting
STATEMENT: >>>
The subsystem shall report when a remote audio file becomes unavailable during
playback such that playback cannot continue.
<<<
RELATIONS:
- TYPE: Parent
  VALUE: SR-128

[[/SECTION]]

[[SECTION]]
TITLE: Remote Audio File Playback Recovery

[REQUIREMENT]
UID: APSSR-083
TITLE: Remote Audio File Playback Resumption
STATEMENT: >>>
The subsystem shall support resuming interrupted remote audio playback when the 
remote audio file becomes accessible again.
<<<
RELATIONS:
- TYPE: Parent
  VALUE: SR-138

[[/SECTION]]

[[/SECTION]]

[[SECTION]]
TITLE: Audio Playback

[[SECTION]]
TITLE: Audio Playback Fidelity

[REQUIREMENT]
UID: APSSR-084
TITLE: Audio Decoding Fidelity
STATEMENT: >>>
The subsystem shall decode supported audio data without introducing additional 
loss of audio information.
<<<
RELATIONS:
- TYPE: Parent
  VALUE: SR-023

[REQUIREMENT]
UID: APSSR-085
TITLE: Lossless Audio Decoding Fidelity
STATEMENT: >>>
The subsystem shall support reproducing the original audio sample values when 
decoding losslessly encoded audio data.
<<<
RELATIONS:
- TYPE: Parent
  VALUE: SR-023

[[/SECTION]]

[[SECTION]]
TITLE: Audio Playback Position

[REQUIREMENT]
UID: APSSR-086
TITLE: Current Playback Position Calculation
STATEMENT: >>>
The subsystem shall determine the current playback position of an active audio
track, within the greater of 1 microsecond or the temporal resolution of the 
active audio track.
<<<
RELATIONS:
- TYPE: Parent
  VALUE: SR-024

[REQUIREMENT]
UID: APSSR-087
TITLE: Current Playback Position Availability
STATEMENT: >>>
The subsystem shall make the current playback position of an active audio track
available upon request.
<<<
RELATIONS:
- TYPE: Parent
  VALUE: SR-025

[REQUIREMENT]
UID: APSSR-088
TITLE: Elapsed Playback Time Calculation
STATEMENT: >>>
The subsystem shall determine the cumulative duration for which the active 
audio track has been playing.
<<<
RELATIONS:
- TYPE: Parent
  VALUE: SR-026

[REQUIREMENT]
UID: APSSR-089
TITLE: Elapsed Playback Time Availability
STATEMENT: >>>
The subsystem shall make the elapsed playback time of an active audio track
available upon request.
<<<
RELATIONS:
- TYPE: Parent
  VALUE: SR-026

[REQUIREMENT]
UID: APSSR-090
TITLE: Seeking Position Acceptance
STATEMENT: >>>
The subsystem shall support seeking to a requested playback position within
the greater of 1 microsecond or the temporal resolution of the active audio 
track.
<<<
RELATIONS:
- TYPE: Parent
  VALUE: SR-028

[REQUIREMENT]
UID: APSSR-091
TITLE: Seeking Position Accuracy
STATEMENT: >>>
The subsystem shall accept a request to seek to a playback position within the 
duration of the active audio track.
<<<
RELATIONS:
- TYPE: Parent
  VALUE: SR-027

[REQUIREMENT]
UID: APSSR-092
TITLE: Remaining Playback Time Calculation
STATEMENT: >>>
The subsystem shall determine the estimated time remaining until the end of an 
active audio track, accounting for its current playback position and playback 
speed.
<<<
RELATIONS:
- TYPE: Parent
  VALUE: SR-029

[REQUIREMENT]
UID: APSSR-093
TITLE: Remaining Playback Time Availability
STATEMENT: >>>
The subsystem shall make the current playback time of an active audio track
available upon request.
<<<
RELATIONS:
- TYPE: Parent
  VALUE: SR-029

[[/SECTION]]

[[SECTION]]
TITLE: Operating System Media integration

[REQUIREMENT]
UID: APSSR-094
TITLE: Playback Information Availability
STATEMENT: >>>
The subsystem shall make the currently playing track's available playback
information accessible through the operating system's media-control interface.
<<<
RELATIONS:
- TYPE: Parent
  VALUE: SR-030

[REQUIREMENT]
UID: APSSR-095
TITLE: Playback Metadata Availability
STATEMENT: >>>
The subsystem shall make the currently playing track's available metadata
accessible through the operating system's media-control interface, where
supported by that interface.
<<<
RELATIONS:
- TYPE: Parent
  VALUE: SR-031

[REQUIREMENT]
UID: APSSR-096
TITLE: Operating System Playback Control
STATEMENT: >>>
The subsystem shall support playback control commands received through the 
operating system's media-control interface, where supported by that interface.
<<<
RELATIONS:
- TYPE: Parent
  VALUE: SR-032

[[/SECTION]]

[[/SECTION]]

[[SECTION]]
TITLE: Audio Playback Customization

[[SECTION]]
TITLE: Playback Speed Customization

[REQUIREMENT]
UID: APSSR-097
TITLE: Playback Speed Independence
STATEMENT: >>>
The subsystem shall adjust the playback speed without changing the playback
pitch.
<<<
RELATIONS:
- TYPE: Parent
  VALUE: SR-035

[REQUIREMENT]
UID: APSSR-098
TITLE: Playback Speed Acceptance
STATEMENT: >>>
The subsystem shall accept requests to adjust the playback speed of the active 
track to values within its supported range.
<<<
RELATIONS:
- TYPE: Parent
  VALUE: SR-033

[REQUIREMENT]
UID: APSSR-099
TITLE: Playback Speed Rejection
STATEMENT: >>>
The subsystem shall report the rejection of requests to adjust the playback 
speed of the active track to values outside of the supported range.
<<<
RELATIONS:
- TYPE: Parent
  VALUE: SR-033

[REQUIREMENT]
UID: APSSR-100
TITLE: Playback Speed Range
STATEMENT: >>>
The subsystem shall support playback speeds from 0.5x to 2.0x inclusive, with 
1.0x being the default playback speed.
<<<
RELATIONS:
- TYPE: Parent
  VALUE: SR-034

[REQUIREMENT]
UID: APSSR-101
TITLE: Playback Speed Maintenance
STATEMENT: >>>
The subsystem shall maintain the set playback speed according to playback speed
persistence configuration settings, with track specific being the default.
<<<
RELATIONS:
- TYPE: Parent
  VALUE: SR-034

[REQUIREMENT]
UID: APSSR-102
TITLE: Playback Speed Persistence Configuration
STATEMENT: >>>
The subsystem shall support configuring playback speed persistence as:
- Permanent: Retained across application sessions,
- Application Session: Retained until the application closes,
- Playback Session: Retained until playback is stopped,
- Track Specific: Reset to 1.0x when the active track changes.
<<<
RELATIONS:
- TYPE: Parent
  VALUE: SR-034
- TYPE: Parent
  VALUE: SR-038

[REQUIREMENT]
UID: APSSR-103
TITLE: Playback Speed Settings Request
STATEMENT: >>>
Upon request, the subsystem shall return the currently active playback speed 
settings.
<<<
RELATIONS:
- TYPE: Parent
  VALUE: SR-034
- TYPE: Parent
  VALUE: SR-039

[[/SECTION]]

[[SECTION]]
TITLE: Playback Pitch Customization

[REQUIREMENT]
UID: APSSR-104
TITLE: Playback Pitch Independence
STATEMENT: >>>
The subsystem shall adjust the playback pitch without changing the playback
speed.
<<<
RELATIONS:
- TYPE: Parent
  VALUE: SR-035

[REQUIREMENT]
UID: APSSR-105
TITLE: Playback Pitch Acceptance
STATEMENT: >>>
The subsystem shall accept requests to adjust the playback pitch of the active 
track to values within its supported range.
<<<
RELATIONS:
- TYPE: Parent
  VALUE: SR-035

[REQUIREMENT]
UID: APSSR-106
TITLE: Playback Pitch Rejection
STATEMENT: >>>
The subsystem shall report the rejection of requests to adjust the playback 
pitch of the active track to values outside of the supported range.
<<<
RELATIONS:
- TYPE: Parent
  VALUE: SR-035

[REQUIREMENT]
UID: APSSR-107
TITLE: Playback Pitch Range
STATEMENT: >>>
The subsystem shall support playback pitch adjustments from -6 to +6 semitones 
inclusive, with 0 semitones being the default playback pitch.
<<<
RELATIONS:
- TYPE: Parent
  VALUE: SR-036

[REQUIREMENT]
UID: APSSR-108
TITLE: Playback Pitch Maintenance
STATEMENT: >>>
The subsystem shall maintain the set playback pitch according to the configured
playback pitch persistence configuration settings, with track specific being 
the default.
<<<
RELATIONS:
- TYPE: Parent
  VALUE: SR-036

[REQUIREMENT]
UID: APSSR-109
TITLE: Playback Pitch Persistence Configuration
STATEMENT: >>>
The subsystem shall support configuring playback pitch persistence as:
- Permanent: Retained across application sessions,
- Application Session: Retained until the application closes,
- Playback Session: Retained until playback is stopped,
- Track Specific: Reset to 0 semitones when the active track changes.
<<<
RELATIONS:
- TYPE: Parent
  VALUE: SR-036
- TYPE: Parent
  VALUE: SR-038

[REQUIREMENT]
UID: APSSR-110
TITLE: Playback Pitch Settings Request
STATEMENT: >>>
Upon request, the subsystem shall return the currently active playback pitch 
settings.
<<<
RELATIONS:
- TYPE: Parent
  VALUE: SR-036
- TYPE: Parent
  VALUE: SR-039

[[/SECTION]]

[[SECTION]]
TITLE: Playback Volume Customization

[REQUIREMENT]
UID: APSSR-111
TITLE: Playback Volume Acceptance
STATEMENT: >>>
The subsystem shall accept requests to adjust the playback volume of the active 
track to values within its supported range.
<<<
RELATIONS:
- TYPE: Parent
  VALUE: SR-037

[REQUIREMENT]
UID: APSSR-112
TITLE: Playback Volume Rejection
STATEMENT: >>>
The subsystem shall report the rejection of requests to adjust the playback 
volume of the active track to values outside of the supported range.
<<<
RELATIONS:
- TYPE: Parent
  VALUE: SR-037

[REQUIREMENT]
UID: APSSR-113
TITLE: Playback Volume Range
STATEMENT: >>>
The subsystem shall support playback volume adjustments from 0% to 150% of the
reference amplitude inclusive, with 100% being the default playback volume.
<<<
RELATIONS:
- TYPE: Parent
  VALUE: SR-037

[REQUIREMENT]
UID: APSSR-114
TITLE: Playback Volume Maintenance
STATEMENT: >>>
The subsystem shall maintain the set playback volume according to the 
configured playback volume persistence configuration settings, with application 
session persistence being the default.
<<<
RELATIONS:
- TYPE: Parent
  VALUE: SR-037

[REQUIREMENT]
UID: APSSR-115
TITLE: Playback Volume Persistence Configuration
STATEMENT: >>>
The subsystem shall support configuring playback volume persistence as:
- Permanent: Retained across application sessions,
- Application Session: Retained until the application closes,
- Playback Session: Retained until playback is stopped,
- Track Specific: Reset to 100% when the active track changes.
<<<
RELATIONS:
- TYPE: Parent
  VALUE: SR-037
- TYPE: Parent
  VALUE: SR-038

[REQUIREMENT]
UID: APSSR-116
TITLE: Playback Volume Settings Request
STATEMENT: >>>
Upon request, the subsystem shall return the currently active playback volume 
settings.
<<<
RELATIONS:
- TYPE: Parent
  VALUE: SR-037
- TYPE: Parent
  VALUE: SR-039

[[/SECTION]]

[[/SECTION]]

[[SECTION]]
TITLE: Playback Configuration Settings

[TEXT]
STATEMENT: >>>
Currently Volume Normalisation, Mono Playback, Channel Swapping and Channel 
Muting are written as requirements.

Considerations will be made for:
- Channel Balance

- Equaliser
- Audio Filters (High-pass, Low-pass, Band-pass and Notch Filters)

- Dynamic-range Compression
- Limiter
- Expander
- Noise Gate
- Automatic Gain Control (AGC)
- Loudness Normalisation
<<<

[[SECTION]]
TITLE: Volume Normalisation

[REQUIREMENT]
UID: APSSR-117
TITLE: Volume Normalisation Configuration
STATEMENT: >>>
The subsystem shall allow volume normalisation to be enabled or disabled.
<<<
RELATIONS:
- TYPE: Parent
  VALUE: SR-038

[REQUIREMENT]
UID: APSSR-118
TITLE: Volume Normalisation Application
STATEMENT: >>>
The subsystem shall adjust the playback level of an active audio track to
achieve a consistent perceived loudness between tracks when volume 
normalisation is enabled.
<<<
RELATIONS:
- TYPE: Parent
  VALUE: SR-038

[REQUIREMENT]
UID: APSSR-119
TITLE: Volume Normalisation Settings Request
STATEMENT: >>>
Upon request, the subsystem shall return the currently active volume 
normalisation settings.
<<<
RELATIONS:
- TYPE: Parent
  VALUE: SR-039

[[/SECTION]]

[[SECTION]]
TITLE: Mono Playback

[REQUIREMENT]
UID: APSSR-120
TITLE: Mono Playback Configuration
STATEMENT: >>>
The subsystem shall allow mono playback to be enabled or disabled.
<<<
RELATIONS:
- TYPE: Parent
  VALUE: SR-038

[REQUIREMENT]
UID: APSSR-121
TITLE: Mono Playback Application
STATEMENT: >>>
The subsystem shall combine the left and right audio channels into a mono 
output when mono playback is enabled.
<<<
RELATIONS:
- TYPE: Parent
  VALUE: SR-038

[REQUIREMENT]
UID: APSSR-122
TITLE: Mono Playback Settings Request
STATEMENT: >>>
Upon request, the subsystem shall return the currently active mono playback 
settings.
<<<
RELATIONS:
- TYPE: Parent
  VALUE: SR-039

[[/SECTION]]

[[SECTION]]
TITLE: Channel Swapping

[REQUIREMENT]
UID: APSSR-123
TITLE: Channel Swapping Configuration
STATEMENT: >>>
The subsystem shall allow channel swapping to be enabled or disabled.
<<<
RELATIONS:
- TYPE: Parent
  VALUE: SR-038

[REQUIREMENT]
UID: APSSR-124
TITLE: Channel Swapping Application
STATEMENT: >>>
The subsystem shall exchange the left and right audio channels when channel 
swapping is enabled.
<<<
RELATIONS:
- TYPE: Parent
  VALUE: SR-038

[REQUIREMENT]
UID: APSSR-125
TITLE: Channel Swapping Settings Request
STATEMENT: >>>
Upon request, the subsystem shall return the currently active channel swapping 
settings.
<<<
RELATIONS:
- TYPE: Parent
  VALUE: SR-039

[[/SECTION]]

[[SECTION]]
TITLE: Channel Muting

[REQUIREMENT]
UID: APSSR-126
TITLE: Left Channel Muting Configuration
STATEMENT: >>>
The subsystem shall allow the left audio channel to be muted or unmuted.
<<<
RELATIONS:
- TYPE: Parent
  VALUE: SR-038

[REQUIREMENT]
UID: APSSR-127
TITLE: Right Channel Muting Configuration
STATEMENT: >>>
The subsystem shall allow the right audio channel to be muted or unmuted.
<<<
RELATIONS:
- TYPE: Parent
  VALUE: SR-038

[REQUIREMENT]
UID: APSSR-128
TITLE: Channel Muting Application
STATEMENT: >>>
The subsystem shall suppress audio output from each channel configured to be 
muted, after applying any configured channel swapping.
<<<
RELATIONS:
- TYPE: Parent
  VALUE: SR-038

[REQUIREMENT]
UID: APSSR-129
TITLE: Channel Muting Settings Request
STATEMENT: >>>
Upon request, the subsystem shall return the currently active channel muting 
settings.
<<<
RELATIONS:
- TYPE: Parent
  VALUE: SR-039

[[/SECTION]]

[[/SECTION]]
