[DOCUMENT]
TITLE: Business Requirements
UID: YAAP-BR
DATE: @GIT_COMMIT_DATETIME
PREFIX: BR-

[[SECTION]]
TITLE: Introduction

[TEXT]
STATEMENT: >>>
This document defines the business requirements for Yet Another Audio Player 
(Yaap), a time accurate desktop audio player.

Yaap provides users with an audio library and playback experience.
<<<

[[/SECTION]]

[[SECTION]]
TITLE: Audio Playback

[[SECTION]]
TITLE: Supported Audio Playback

[REQUIREMENT]
UID: BR-001
TITLE: Supported audio Formats
STATEMENT: >>>
Yaap shall support playback of a range of audio formats and codecs.
<<<

[REQUIREMENT]
UID: BR-002
TITLE: Storing Audio Playback Locally
STATEMENT: >>>
Yaap shall provide the ability to play supported audio files stored locally on
their devices.
<<<

[REQUIREMENT]
UID: BR-003
TITLE: Storing Audio Playback Externally
STATEMENT: >>>
Yaap shall provide the ability to play supported audio files stored on
supported, linked cloud providers.
<<<

[[/SECTION]]

[[SECTION]]
TITLE: Audio Playback Functionality

[REQUIREMENT]
UID: BR-004
TITLE: Audio Playback Quality
STATEMENT: >>>
Yaap shall provide accurate audio playback appropriate for high-quality audio
collections.
<<<

[REQUIREMENT]
UID: BR-005
TITLE: Audio Playback Position
STATEMENT: >>>
Yaap shall provide an accurate representation of the current or requested
playback position of an audio track.
<<<

[REQUIREMENT]
UID: BR-006
TITLE: Audio Playback Customization
STATEMENT: >>>
Yaap shall allow for playback characteristic customizations such as speed,
pitch, volume, and audio processing.
<<<

[[/SECTION]]

[[/SECTION]]

[[SECTION]]
TITLE: Organisation

[[SECTION]]
TITLE: Audio Library

[REQUIREMENT]
UID: BR-007
TITLE: Audio Library
STATEMENT: >>>
Yaap shall provide a persistent library containing supported audio tracks.
<<<

[[/SECTION]]

[[SECTION]]
TITLE: Track Metadata

[REQUIREMENT]
UID: BR-008
TITLE: Searching, Sorting and Filtering
STATEMENT: >>>
Yaap shall allow for the discovery of tracks through searching, sorting,
filtering and tagging management.
<<<

[REQUIREMENT]
UID: BR-009
TITLE: Track Metadata Management
STATEMENT: >>>
Yaap shall allow for the viewing, managing, and where appropriate modification
of track metadata.
<<<

[[/SECTION]]

[[SECTION]]
TITLE: Library Activity

[REQUIREMENT]
UID: BR-010
TITLE: Library Activity Provision
STATEMENT: Yaap shall provide library activity information.

[[/SECTION]]

[[/SECTION]]

[[SECTION]]
TITLE: Queue, Playlist and Collection Management

[REQUIREMENT]
UID: BR-011
TITLE: Playlist and Collection Organisation
STATEMENT: >>>
Yaap shall allow for the creation, modification and organisation of
playlists and collections.
<<<

[REQUIREMENT]
UID: BR-012
TITLE: Playback Queue Management
STATEMENT: Yaap shall be able to create and modify its playback queues.

[REQUIREMENT]
UID: BR-013
TITLE: Playback Order
STATEMENT: Yaap shall allow users to control the order of tracks being played.

[[/SECTION]]

[[SECTION]]
TITLE: Personalisation

[REQUIREMENT]
UID: BR-014
TITLE: User Preferences
STATEMENT: >>>
Yaap shall allow users to configure app settings.
<<<

[REQUIREMENT]
UID: BR-015
TITLE: Internationalisation
STATEMENT: Yaap shall allow for the application language to be changed.

[[/SECTION]]

[[SECTION]]
TITLE: Analytics

[REQUIREMENT]
UID: BR-016
TITLE: Listening Analytics
STATEMENT: >>>
Yaap shall allow for the analysis of listening behaviour and audio consumption.
<<<

[[/SECTION]]

[[SECTION]]
TITLE: Interoperability

[REQUIREMENT]
UID: BR-017
TITLE: Application Interoperability 
STATEMENT: >>>
Yaap shall support interoperability with external applications, services,
and devices.
<<<

[[/SECTION]]

[[SECTION]]
TITLE: User Interaction

[REQUIREMENT]
UID: BR-018
TITLE: Accessing Application Functionality
STATEMENT: >>>
Yaap shall provide access to functionality through intuitive interfaces.
<<<

[[/SECTION]]

[[SECTION]]
TITLE: Data Management

[REQUIREMENT]
UID: BR-019
TITLE: Operation Recovery
STATEMENT: Yaap shall allow reversible modifications to be undone and redone.

[REQUIREMENT]
UID: BR-020
TITLE: Importing and Exporting App and User Data 
STATEMENT: Yaap shall be able to import and export application and user data.

[[/SECTION]]

[[SECTION]]
TITLE: Lyrics

[REQUIREMENT]
UID: BR-021
TITLE: Displaying Lyrics
STATEMENT: >>>
Yaap shall provide the ability to view and edit lyrics associated with audio
tracks.
<<<

[REQUIREMENT]
UID: BR-022
TITLE: Lyrics Variants
STATEMENT: >>>
Yaap shall support the use of alternative lyric versions and translations.
<<<

[REQUIREMENT]
UID: BR-023
TITLE: Downloading Lyrics
STATEMENT: >>>
Yaap shall provide the ability to download lyrics associated with audio tracks.
<<<

[[/SECTION]]

[[SECTION]]
TITLE: Audio Visualisation

[REQUIREMENT]
UID: BR-024
TITLE: Audio Visualisation
STATEMENT: >>>
Yaap shall provide visual representations of audio during playback.
<<<

[[/SECTION]]
